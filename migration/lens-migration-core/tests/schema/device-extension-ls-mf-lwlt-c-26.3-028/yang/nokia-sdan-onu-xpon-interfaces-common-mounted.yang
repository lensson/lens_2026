module nokia-sdan-onu-xpon-interfaces-common-mounted {
  yang-version 1.1;
  namespace "http://www.nokia.com/Fixed-Networks/BBA/yang/nokia-sdan-onu-xpon-interfaces-common-mounted";
  prefix nokia-sdan-onuxpon-ifc-mounted;

  organization
    "Nokia";
  contact
    "Comments or questions about this Nokia YANG module should be
    directed to <mailto:isam.yang@nokia.com>.";
  description
    "This module contains a collection of YANG definitions for
    supporting Nokia specific requirements as applicable to its
    access network equipment.

    Specifically, this module contains a collection of YANG definitions
    to provide sufficient troubleshooting information for the configuration
    errors occurred during configuration transactions.

    This specification is published by Nokia under Non-Disclosure
    Agreement(s) (NDA) with specific parties and has to be considered
    as Confidential Information as defined in such NDA. Nokia
    reserves the right to revise this document for any reason,
    including but not limited to conformity with standards
    promulgated by various agencies, utilisation of advances in the
    state of the technical areas, or the reflection of changes in the
    design of any equipment, techniques, or procedures described or
    referred to herein.

    The product specifications and other technical or performance
    information contained herein are subject to change without
    notice. Updates of this document will be issued under the above
    NDA's.

    Nokia makes no representation or warranty, expressed or implied,
    with respect to the sufficiency, accuracy, or utility of any
    information or opinion contained herein. Nokia expressly advises
    that any use of for any purpose or reliance upon this technical
    reference is at the risk of the user and that Nokia shall not be
    liable for any damage or injury incurred by any person arising
    out of the sufficiency, accuracy, or utility of any information
    or opinion contained herein.

    This document is not to be construed as a suggestion to any
    manufacturer to modify or change any of its products, nor does
    this document represent any commitment by Nokia to sell or
    purchase any product. Nothing contained herein shall be construed
    as conferring by implication, estoppel, or otherwise any license
    or right under any patent, whether or not the use of any
    information herein necessarily employs an invention of any
    existing or later issued patent.

    Nokia reserves the right not to offer any or all of these
    products and to withdraw any or all of them at any future time.

    Copyright (C) 2022, Nokia. All Rights Reserved.";

  revision 2024-12-10 {
    description
      "Add new group 'onu-phy-resources-capacities'.";
    reference "Nokia specific";
  }
  
  revision 2024-04-12 {
    description
      "Initial revision.";
    reference "Nokia specific";
  }

  grouping onu-queue-status-report {
    description
      "xPON state data from the Optical Network Unit (ONU)
      physical device. This data is fetched from the ONU physical
      device, when present.";
    leaf onu-queue-status-report {
      type boolean;
      description
        "This Boolean attribute indicates the ONU's capability to
        report its queue status for DBA, by means of OMCI 'SR
        indication' attribute in ANI-G ME (ref. G.988 Clause
        9.2.1). The value true means that status reporting is
        available for all T-CONTs that are associated with the
        ANI.";
    reference
        "G.988: 9.2.1 ANI-G.";
    }
  }

  identity encryption-mode-base {
    description
      "This identity is used to denote different encryption modes.";
  }

  identity encryption-mode-unrecognized {
    base encryption-mode-base;
    description
      "This identity is used to denote an encryption mode that
      is not recognized by the OLT.";
  }

  identity encryption-mode-aes-128 {
    base encryption-mode-base;
    description
      "This identity is used to denote the encryption mode is AES-128.";
  }

  identity encryption-mode-aes-256 {
    base encryption-mode-base;
    description
      "This identity is used to denote the encryption mode is AES-256.";
  }

  identity encryption-mode-camellia-128 {
    base encryption-mode-base;
    description
      "This identity is used to denote the encryption mode is camellia-128.";
  }

  identity encryption-mode-camellia-256 {
    base encryption-mode-base;
    description
      "This identity is used to denote the encryption mode is camellia-256.";
  }

  identity encryption-mode-sm4 {
    base encryption-mode-base;
    description
      "This identity is used to denote the encryption mode is SM4.";
  }
  grouping onu-security-report {
    description
      "xPON state data from the Optical Network Unit (ONU)
      physical device. This data includes security capability which is
      fetched from the ONU physical device, and also the security mode
      which is set by Onu Engine and used by OLT&ONU.";

    leaf-list onu-encryption-capability {
      type identityref {
        base encryption-mode-base;
      }
      description
        "The encryption mode(s) that the ONU is capable
        to apply. Ref. ITU-T G.988, Clause 9.1.2,
        ONU2-G ME, 'security capability' attribute.";
      reference
        "ITU-T G.988 clause 9.1.2 ONU2-G - Security capability attribute";
    }

    leaf actual-onu-encryption-mode {
      type identityref {
        base encryption-mode-base;
      }
      description
        "The actual encryption mode selected for the ONU.
        Ref. ITU-T G.988, Clause 9.1.2, ONU2-G ME,
        'security mode' attribute. All secure GEM ports
        in an ONU must use the same security mode at any
        given time. Note however that this data node does
        not imply that all channels (e.g. GEM ports or OMCI
        channel) are encrypted; that process is negotiated
        per GEM port at the PLOAM layer. It only signifies
        the security mode to be used on the GEM ports that
        the OLT may choose to encrypt. ";
      reference
        "ITU-T G.988 clause ONU2-G - Security mode attribute";
    }
  }

  grouping onu-phy-resources-capacities {
    description
      "Report physical resources capacities from the Optical Network Unit (ONU)
      physical device. This data is fetched from the ONU physical
      device, when present.";
    leaf total-t-cont-number-capacity {
      type uint16;
      description
        "This attribute indicates the total number of T-CONTs
        that can be supported on this ANI, by means of OMCI 'Total
        T-CONT number' attribute in ANI-G ME (ref. G.988 Clause
        9.2.1).";
      reference
        "G.988: 9.2.1 ANI-G.";
    }

    leaf total-gem-port-id-number-capacity {
      type uint16;
      description
        "This attribute reports the total number of GEM port-IDs
        supported by the ONU, by means of OMCI 'Total GEM port-ID number
        number' attribute in ONU2-G ME (ref. G.988 Clause
        9.1.2).";
      reference
        "G.988: 9.1.2 ONU2-G.";
    }
  }
}
