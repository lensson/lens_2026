module bbf-fiber-rogue-nodes{
  namespace "urn:broadband-forum-org:yang:bbf-fiber-rogue-nodes";
  yang-version 1.1;

  prefix bbf-fiber-rogue;

  import ietf-interfaces {
    prefix if;
  }

  import bbf-xpon {
    prefix bbf-xpon;
  }

  import bbf-xpon-types {
    prefix bbf-xpon-types;
  }

  organization "Nokia";
  contact "isam.yang@nokia.com";

  description
    "This specification is published by Nokia under Non-Disclosure
    Agreement(s) (NDA) with specific parties and has to be considered
    as Confidential Information as defined in such NDA. Nokia reserves
    the right to revise this document for any reason, including but
    not limited to conformity with standards promulgated by various
    agencies, utilization of advances in the state of the technical
    areas, or the reflection of changes in the design of any
    equipment, techniques, or procedures described or referred to
    herein.

    The product specifications and other technical or performance
    information contained herein are subject to change without notice.
    Updates of this document will be issued under the above NDA's.

    Nokia makes no representation or warranty, expressed or implied,
    with respect to the sufficiency, accuracy, or utility of any
    information or opinion contained herein. Nokia expressly advises
    that any use of for any purpose or reliance upon this technical
    reference is at the risk of the user and that Nokia shall not be
    liable for any damage or injury incurred by any person arising out
    of the sufficiency, accuracy, or utility of any information or
    opinion contained herein.

    This document is not to be construed as a suggestion to any
    manufacturer to modify or change any of its products, nor does
    this document represent any commitment by Nokia to sell or
    purchase any product. Nothing contained herein shall be construed
    as conferring by implication, estoppel, or otherwise any license
    or right under any patent, whether or not the use of any
    information herein necessarily employs an invention of any
    existing or later issued patent.

    Nokia reserves the right not to offer any or all of these products
    and to withdraw any or all of them at any future time.

    Copyright (C) 2022, Nokia. All Rights Reserved";

  revision 2024-09-25 {
    description
      "remove some leaves not supported";
    reference
      "TBD";
  }

  revision 2019-04-28 {
    description
      "Initial revision.";
    reference
      "TBD";
  }

identity rogue-test-type {
  description
	"This identity is used to denote the rogue test type.";
}

identity stuck-laser-on {
  base rogue-test-type;
  description
	"This identity is used to denote that the rogue test type is stuck laser test.";
}

identity rogue-mitigation-action {
  description
	"This identity is used to denote the mitigation action to be taken for ONUs suspected rogue.";
}

identity none {
  base rogue-mitigation-action;
  description
	"This identity is used to denote that no action will be taken.";
}

identity deactivate-onu {
  base rogue-mitigation-action;
  description
	"This identity is used to denote that OLT will deactivate the ONUs suspected rogue.";
}

identity rogue-test-trigger {
  description
	"This identity is used to denote the trigger of background rogue test.";
}

identity pon-los {
  base rogue-test-trigger;
  description
	"This identity is used to denote that background rogue test will be triggered by pon-los.";
}

identity rogue-test-occurrence {
  description
	"This identity is used to denote the rogue test occurrence.";
}

identity background {
  base rogue-test-occurrence;
  description
	"This identity is used to denote background rogue test.";
}

identity manual {
  base rogue-test-occurrence;
  description
	"This identity is used to denote on demand rogue test.";
}

identity rogue-mitigation-reason {
  description
	"This identity is used to denote mitigation reason of ONU.";
}

identity stuck-laser {
  base rogue-mitigation-reason;
  description
	"This identity is used to denote that the mitigation reason is stuck-laser test.";
}

identity onu-troubleshoot-action {
  description
	"This identity is used to denote the action to be taken to ONU for troubleshooting.";
}

identity deactivate {
  base onu-troubleshoot-action;
  description
    "This identity is used to denote that OLT will deactivate the ONU.";
}

identity enable {
  base onu-troubleshoot-action;
  description
	"This identity is used to denote that OLT will enable the ONU.";
}

typedef rogue-profile-ref {
  type leafref {
	path '/bbf-fiber-rogue:rogue-test-profile/bbf-fiber-rogue:name';
  }
  description
	"The name of the referenced rogue test profile.";
}

typedef name-ascii64 {
  type string {
	length "1..64";
	pattern '[ -~]*';
  }
  description
	"Used where a name is represented using at least 1 and no more
	 than 64 ASCII characters.";
}

list rogue-test-profile {
  key "name";
  description
	"A list of rogue test profiles.";

  leaf name {
	type name-ascii64;
	description
	  "Name of the rogue test profile.";
  }
  leaf test-type {
	type identityref {
	  base rogue-test-type;
	}
	mandatory true;
	description
	  "Indicates the test type of rogue test.";
  }
  leaf mitigation-action {
	type identityref {
	  base rogue-mitigation-action;
	}
	mandatory true;
	description
	  "Indicates the mitigation action to ONUs suspected rogue.";
  }
}

augment '/if:interfaces/if:interface/bbf-xpon:channel-termination' {

	list background-rogue-test {
	  key "name";
	  unique "start-trigger";
	  description
		"A list of background rogue test.";

	  leaf name {
		type name-ascii64;
		description
		  "Name of the background rogue test.";
	  }
	  leaf rogue-test-profile-ref {
		type rogue-profile-ref;
		mandatory true;
		description
		  "A reference to a rogue test profile.";
	  	}
	  leaf activated {
		type boolean;
		default "false";
		description
		  "Used to Enable/Disable background rogue test.";
	  }
	  leaf start-trigger {
     	type identityref {
	      base rogue-test-trigger;
	    }
		mandatory true;
		description
		  "Indicates the trigger of background rogue test.";
	  }
	}

  action manual-rogue-test-start {
	description
	  "This action starting a manual rogue test on a given channel-termination.";
	input {
	  leaf rogue-test-profile-ref {
		type rogue-profile-ref;
		mandatory true;
		description
		  "A reference to a rogue test profile.";
	  }
	  leaf manual-test-name {
		type name-ascii64;
		mandatory true;
		description
		  "The name assigned to this manual rogue test.";
		}
	}
	output {
	  leaf rogue-test-request-status {
		type identityref {
		  base bbf-xpon-types:action-request-status;
		}
		description
		  "Indicates what the OLT is doing when receiving the
		   rogue test request action. The OLT can for instance
		   indicate that the request is in progress or has been rejected.";
	  }

	  leaf rogue-test-request-reject-string {
		when
		  "../rogue-test-request-status
					  != 'bbf-xpon-types:request-being-processed'" {
		  description
			"only valid when the OLT has rejected the rogue test
			 request.";
		}
		type string;
		description
		  "A text string indicating the reason why the OLT
		   rejected the action.";
	  }
	}
  }

  action rogue-test-stop {
	description
	  "This action stopping the rogue test.";
	input {
	  leaf test-name {
		type name-ascii64;
		mandatory true;
		description
		  "The name of the rogue test to be stopped.";
		}
	}
	output {
	  leaf rogue-test-request-status {
		type identityref {
		  base bbf-xpon-types:action-request-status;
		}
		description
		  "Indicates what the OLT is doing when receiving the
		   rogue test request action. The OLT can for instance
		   indicate that the request is in progress or has been rejected.";
	  }

	  leaf rogue-test-request-reject-string {
		when
		  "../rogue-test-request-status
					  != 'bbf-xpon-types:request-being-processed'" {
		  description
			"only valid when the OLT has rejected the rogue test
			 request.";
		}
		type string;
		description
		  "A text string indicating the reason why the OLT
		   rejected the action.";
	  }
	}
  }


  list running-rogue-test {
	key "name";
	config false;
	description
	  "A list of running rogue test.";

	leaf name {
	  type name-ascii64;
	  description
		"Name of the running rogue test.";
	}
	leaf rogue-test-occurrence {
	 type identityref {
	   base rogue-test-occurrence;
	 }
	 description
	   "Indicates the rogue test occurrence.";
   }
  }

  action onu-troubleshoot {
	description
	  "This action directly acting on the ONU via PLOAM.";
	input {
	  leaf onu-serial-number {
        type string {
          pattern '([a-zA-Z0-9]{4}[0-9a-fA-F]{8})?';
        }
		mandatory true;
        description
          "The serial number of the ONU. The serial number is unique for each ONU. It contains the vendor ID and vendor specific serial number. The first four bytes are an ASCII-encoded vendor ID four letter mnemonic. The second four bytes are a binary encoded serial number, under the control of the ONU vendor.";
        reference
          "ITU-T G.984.3, section 9.2.4.1.";
      }
	  leaf action-to-onu {
		type identityref {
		  base onu-troubleshoot-action;
		}
		mandatory true;
		description
		  "Indicates the action that OLT send to ONU via PLOAM.";
	  }
	}
	output {
	  leaf rogue-test-request-status {
		type identityref {
		  base bbf-xpon-types:action-request-status;
		}
		description
		  "Indicates what the OLT is doing when receiving the
		   rogue test request action. The OLT can for instance
		   indicate that the request is in progress or has been rejected.";
	  }

	  leaf rogue-test-request-reject-string {
		when
		  "../rogue-test-request-status
					  != 'bbf-xpon-types:request-being-processed'" {
		  description
			"only valid when the OLT has rejected the rogue test
			 request.";
		}
		type string;
		description
		  "A text string indicating the reason why the OLT
		   rejected the action.";
	  }
	}
  }
 }

augment '/if:interfaces-state/if:interface/bbf-xpon:channel-termination' {
  notification rogue-test-report {
    description
      "Notification reporting the result of a rogue test report.";
    leaf rogue-test-occurrence {
	  type identityref {
	    base rogue-test-occurrence;
	  }
	  description
	    "Indicates the rogue test occurrence.";
    }
    leaf test-name {
	  type name-ascii64;
	  description
	    "Name of the rogue test.";
    }
    list isolated-onu {
      key "serial-number";
      description
	    "A list of ONUs suspected rogue.";
      leaf serial-number {
        type string {
          pattern '([a-zA-Z0-9]{4}[0-9a-fA-F]{8})?';
        }
        description
          "The serial number of the ONU. The serial number is unique for each ONU. It contains the vendor ID and vendor specific serial number. The first four bytes are an ASCII-encoded vendor ID four letter mnemonic. The second four bytes are a binary encoded serial number, under the control of the ONU vendor.";
        reference
          "ITU-T G.984.3, section 9.2.4.1.";
      }
	  leaf onu-id {
	    type uint32 {
		  range "0..1020";
	    }
	    description
	 	 "This is the TC layer ONU-ID identifier.";
	    reference
		   "G.984.3 section 5.5.2
		    G.987.3 section 6.4.2
		    G.9807.1 section C.6.1.5.6
		    G.989.3 section 6.1.5.6";
	  }
	  leaf v-ani-ref {
	    type string;
	    mandatory false;
	    description
		  "The v-ani interface related to this ONU.";
      }
	  leaf mitigation-action-performed {
	    type identityref {
	      base rogue-mitigation-action;
	    }
	    description
		  "Indicates the mitigation action taken for the ONU.";
	  }
	  leaf reason {
	    type identityref {
	      base rogue-mitigation-reason;
	    }
	    description
		  "Indicates the reason of mitigation action taken for the ONU.";
	  }
    }
  }

  container last-rogue-test-report {
    config false;
    description
      "reporting the result of last rogue test.";
    leaf rogue-test-occurrence {
	  type identityref {
	    base rogue-test-occurrence;
	  }
	  description
	    "Indicates the rogue test occurrence.";
    }
    leaf test-name {
	  type name-ascii64;
	  description
	    "Name of the rogue test.";
    }
    list isolated-onu {
      key "serial-number";
      description
	    "A list of ONUs suspected rogue.";
      leaf serial-number {
        type string {
          pattern '([a-zA-Z0-9]{4}[0-9a-fA-F]{8})?';
        }
        description
          "The serial number of the ONU. The serial number is unique for each ONU. It contains the vendor ID and vendor specific serial number. The first four bytes are an ASCII-encoded vendor ID four letter mnemonic. The second four bytes are a binary encoded serial number, under the control of the ONU vendor.";
        reference
          "ITU-T G.984.3, section 9.2.4.1.";
      }
	  leaf onu-id {
	    type uint32 {
		  range "0..1020";
	    }
	    description
	 	 "This is the TC layer ONU-ID identifier.";
	    reference
		   "G.984.3 section 5.5.2
		    G.987.3 section 6.4.2
		    G.9807.1 section C.6.1.5.6
		    G.989.3 section 6.1.5.6";
	  }
	  leaf v-ani-ref {
	    type string;
	    mandatory false;
	    description
		  "The v-ani interface related to this ONU.";
      }
	  leaf mitigation-action-performed {
	    type identityref {
	      base rogue-mitigation-action;
	    }
	    description
		  "Indicates the mitigation action taken for the ONU.";
	  }
	  leaf reason {
	    type identityref {
	      base rogue-mitigation-reason;
	    }
	    description
		  "Indicates the reason of mitigation action taken for the ONU.";
	  }
    }
  }
 }
}
