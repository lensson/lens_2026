submodule bbf-voip-access-gateway-mounted {
  yang-version 1.1;
  belongs-to bbf-sip-voip-mounted  {
	prefix bbf-sip-voip-mounted;
  }

  import bbf-yang-types {
    prefix bbf-yang;
  }
  
  include bbf-sip-profiles-mounted;
  include bbf-sip-types-mounted;
  include bbf-sip-server-redundancy-settings-mounted;
  include bbf-sip-server-redundancy-operational-data-mounted;
  include bbf-voip-access-gateway-operational-data-mounted;
  include bbf-voip-service-providers-mounted;
  include bbf-sip-server-pool-mounted;
  include bbf-sip-signaling-notifications-mounted;
  include bbf-sip-voip-base-mounted;
  include bbf-voicemail-servers-mounted;

  
  organization
    "Broadband Forum <https://www.broadband-forum.org>
     Common YANG Work Area";

  contact
    "Comments or questions about this Broadband Forum YANG module
     should be directed to <mailto:help@broadband-forum.org>.
     Editor:      Frank Desseyn, Nokia
     Editor:      Nadine Staelens, Nokia
     PS Leader:   Joey Boyd, ADTRAN
     PS Leader:   Ken Kerpez, ASSIA
     WA Director: Joey Boyd, ADTRAN
     WA Director: Sven Ooghe, Nokia";

  description
    "This submodule contains the Yang definitions to manage the 
	 Voip Access Gateway (VAG) profile.
     Copyright (c) 2017-2018, Broadband Forum
     Redistribution and use in source and binary forms, with or
     without modification, are permitted provided that the following
     conditions are met:
     1. Redistributions of source code must retain the above copyright
        notice, this list of conditions and the following disclaimer.
     2. Redistributions in binary form must reproduce the above
        copyright notice, this list of conditions and the following
        disclaimer in the documentation and/or other materials
        provided with the distribution.
     3. Neither the name of the copyright holder nor the names of its
        contributors may be used to endorse or promote products
        derived from this software without specific prior written
        permission.
     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.
     The above license is used as a license under copyright only.
     Please reference the Forum IPR Policy for patent licensing terms
     <https://www.broadband-forum.org/ipr-policy>.
     Any moral rights which are necessary to exercise under the above
     license grant are also deemed granted under this license.
     This version of this YANG module is part of TR-383; see
     the TR itself for full legal notices.";

  revision 2020-03-06 {
    description
      "Initial revision.
       * Approval Date:    see revision date above.
       * Publication Date: 2020-03-06.";
    reference
      " ";
  }     

  feature sip-server-redundancy {
	description
      "Indicates support for SIP server redundancy.";
	}

  feature geo-redundancy {
	description
      "Indicates support for geographical redundancy.
       Geographical redundancy may be applied at the 
       level of the SIP server (feature geo-redundancy and
       feature sip-server-redundancy are true) or may
       be applied at the level of the SIP server and the 
       DNS server (feature geo-redundancy and feature 
       sip-server-redundancy and feature dns-server-redundancy
       are true).";
  }

  grouping vag-spec-parameters {
    leaf admin-state {
        type enumeration {
          enum unlocked {
        	  value 1;
        	  description
        	    "The VAG is unlocked.";
          }
          enum locked {
        	  value 2;
        	  description
        	    "The VAG is locked.";
          }					
        }
        default locked;
        description
        	"The administrative state of the VAG.";
    }
    leaf voip-service-provider {
      /*    type voip-service-provider-ref; */
 	  type leafref {
             path "../../../../bbf-sip-voip-mounted:sip-signaling"
                + "/bbf-sip-voip-mounted:voip-service-providers"
	        + "/bbf-sip-voip-mounted:voip-service-provider"
	        + "/bbf-sip-voip-mounted:name";
	  }
          mandatory true;	  
          description
               "Uniquely identifies the Voip Service Provider.";
    }
    leaf vag-sip-register-profile {
 	  /* type bbf-sip-voip-mounted:sip-registerchar-profile-ref;*/
      type leafref {
        path "../../../../bbf-sip-voip-mounted:sip-profiles"
           + "/bbf-sip-voip-mounted:sip-registerchar-profiles"
           + "/bbf-sip-voip-mounted:sip-registerchar-profile"
		   + "/bbf-sip-voip-mounted:name";
      } 	  
	  /*default null-pointer;*/			
 	  description
 		"References the sip register characteristics profile.";
    }
    container sip-service-profile {
      leaf call-flow-file-id { 
        type bbf-yang:string-ascii64;
        description
          "The identity of the sip service profile configuration 
		   file to be used for this VAG.";
      }
      leaf call-flow-file-version {	       
        type string {length "1..32";}
        description
          "The version of the sip service profile configuration
           file.";
      }
      description
	    "Characteristics of the sip service profile."; 
    }
    leaf vag-primary-site-first-hop-sip-servers {
      /*    type bbf-sip-voip-mounted:sip-server-pool-ref; */
 	  type leafref {
              path "../../../../bbf-sip-voip-mounted:sip-signaling"
                 + "/bbf-sip-voip-mounted:sip-server-pools"
                 + "/bbf-sip-voip-mounted:sip-server-pool"
	           + "/bbf-sip-voip-mounted:name";
      }
	  description
	    "References a pool of primary First Hop sip servers
		 for this VAG.";		
    }	
    container vag-backup-site-first-hop-sip-servers {
	if-feature geo-redundancy;
	leaf vag-backup-site-first-hop-sip-servers {
        /*    type bbf-sip-voip-mounted:sip-server-pool-ref;*/
	    type leafref {
              path "../../../../../bbf-sip-voip-mounted:sip-signaling"
                 + "/bbf-sip-voip-mounted:sip-server-pools"
                 + "/bbf-sip-voip-mounted:sip-server-pool"
		   + "/bbf-sip-voip-mounted:name";
            }
	    description
	      "References a pool of backup First Hop sip servers
		   for this VAG.";		
	}
    }
    leaf vag-first-hop-sip-server-validation {
	  type enumeration {
		enum any-sip-server {
		  value 1;					
		  description
			"The NE accepts SIP requests from ANY first hop SIP 
			server, even from a first hop SIP server that does not
			appear in its list of configured / DNS retrieved 
			first hop SIP servers. Or in other words, the NE does
			not perform any check on the source IP@ of an incoming 
			SIP	request.";
		}
		enum current-sip-server {
		  value 2;
		  description
		    "The NE accepts incoming SIP 
			 requests on the condition that
			 the source IP@ of the incoming
			 SIP request equals the IP@ of the
			 first hop SIP server that is 
			 addressed to register the
			 SIP terminations.";
		}
		enum configured-sip-server-list {
		  value 3;
		  description
			"The NE accepts incoming SIP 
			 requests on the condition that the
			 source IP@ of the incoming
			 SIP request equals one of the IP@
			 of the configured / DNS retrieved
			 first hop SIP servers.        
        	 When an incoming SIP request is 
			 rejected, it is
			 replied with a 403 forbidden.";
		}
	  }
	  default any-sip-server;			
	  description
		"Incoming SIP request validation.";
    }
    container vag-prim-site-redundancy {
	  if-feature sip-server-redundancy;
	  leaf vag-primary-site-redundant-sip-servers {
        /*        type bbf-sip-voip-mounted:sip-server-pool-ref; */
		type leafref {
          path "../../../../../bbf-sip-voip-mounted:sip-signaling"
                + "/bbf-sip-voip-mounted:sip-server-pools"
                + "/bbf-sip-voip-mounted:sip-server-pool"
		        + "/bbf-sip-voip-mounted:name";
        }
		description
		  "References a pool of primary site redundant SIP 
		   servers for this VAG.";
	  }
	  uses sip-server-redundancy-settings;
    }
    container vag-backup-site-redundancy {
	  if-feature geo-redundancy;
	  if-feature sip-server-redundancy;
	  leaf vag-backup-site-redundant-sip-servers {
      /*  type bbf-sip-voip-mounted:sip-server-pool-ref;*/
		type leafref {
          path "../../../../../bbf-sip-voip-mounted:sip-signaling"
                + "/bbf-sip-voip-mounted:sip-server-pools"
                + "/bbf-sip-voip-mounted:sip-server-pool"
		        + "/bbf-sip-voip-mounted:name";
        }
		description
		  "References a pool of backup site redundant SIP 
		  servers for this VAG.";
	  }
    }	   	
    leaf voicemail-server {
	  if-feature vm-servers;
	  type leafref {
             path "../../../../bbf-sip-voip-mounted:sip-signaling"
                + "/bbf-sip-voip-mounted:voicemail-servers"
		        + "/bbf-sip-voip-mounted:voicemail-server"
	            + "/bbf-sip-voip-mounted:name";
          }
          description
            "References a voice mail server.";
    }
  }
  
  grouping voip-access-gateway {
    description
      "Defines the parameters included in the voip access 
	   gateway specific profile.";   
	uses vag-spec-parameters;
	uses voip-access-gateway-operational-data;
	uses sip-server-redundancy-operational-data;
	uses sip-vag-notifications;
  }    
}
