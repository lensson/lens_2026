module tailf-aaa {
  namespace "http://tail-f.com/ns/aaa/1.1";
  prefix aaa;
  tailf:id "http://tail-f.com/ns/aaa";

  import ietf-netconf-acm {
    prefix nacm;
  }

  import iana-crypt-hash {
    prefix ianach;
  }

  import tailf-common {
    prefix tailf;
  }

  organization "Tail-f Systems";

  description
    "This module defines the Tail-f AAA data model.";

  revision 2024-11-30 {
    description
      "Released as part of ConfD-8.4 / NCS-6.4.

       Added /aaa/authentication/users/user/local_ipc_access.";
  }

  revision 2023-04-13 {
    description
      "Released as part of ConfD-8.1 / NCS-6.1.

       Mark module as an internal data provider with tailf:internal-dp.";
  }

  revision 2022-04-12 {
    description
      "Released as part of ConfD-7.8 / NCS-5.8.

       Updated range for idle-timeout type.";
  }

  revision 2018-09-12 {
    description
      "Released as part of ConfD-6.5.7 / NSO-4.5.7.

       Added tailf:suppress-echo for /aaa/authentication/users/user/password.";
  }

  revision 2015-06-16 {
    description
      "Released as part of ConfD-6.0 / NSO-4.0.

       Added /aaa/authentication/users/user/change-password action.";
  }

  revision 2014-08-29 {
    description
      "Released as part of ConfD-5.2.1 / NCS-3.2.1.

       Removed max-elements restriction on /aaa/authentication/users/user.";
  }

  revision 2014-06-30 {
    description
      "Released as part of ConfD-5.2 / NCS-3.2.

       Changed passwdStr typedef to use ianach:crypt-hash instead of
       tailf:md5-digest-string.";
  }

  revision 2013-03-07 {
    description
      "Released as part of ConfD-4.2.

       Added nacm:default-deny-all extension for /aaa and /user, and
       nacm:default-deny-write extension for /alias and /session.";
  }

  revision 2012-11-08 {
    description
      "Released as part of ConfD-4.1.

       Removed /aaa/authentication/groups and /aaa/authorization,
       since this functionality is modeled in
       ietf-netconf-acm.yang as augmented by tailf-acm.yang.";
  }

  revision 2011-09-22 {
    description
      "Released as part of ConfD-3.7.";
  }

  revision 2010-06-17 {
    description
      "Released as part of ConfD-3.3.";
  }

  revision 2010-04-22 {
    description
      "Released as part of ConfD-3.2.1.";
  }

  revision 2010-03-18 {
    description
      "Released as part of ConfD-3.2.";
  }

  tailf:internal-dp;

  typedef history {
    type uint64 {
      range "0 .. 8192";
    }
  }
  typedef idle-timeout {
    type uint64 {
      range "0 .. 4294967";
    }
  }
  typedef display-level {
    type uint64 {
      range "1 .. 64";
    }
  }
  typedef passwdStr {
    type ianach:crypt-hash;
  }
  typedef levelInt {
    type int32 {
      range "0 .. 15";
    }
  }
  typedef modeStr {
    type union {
      type string;
      type builtinModes;
    }
  }
  typedef builtinModes {
    type enumeration {
      enum exec;
      enum configure;
    }
  }

  grouping session-params {
    leaf complete-on-space {
      type boolean;
      tailf:info "Enable/disable completion on space";
    }
    leaf ignore-leading-space {
      type boolean;
      tailf:info "Ignore leading whitespace";
    }
    leaf idle-timeout {
      type idle-timeout;
      tailf:info "CLI idle-timeout in seconds";
    }
    leaf paginate {
      type boolean;
      tailf:info "Paginate output from CLI commands";
    }
    leaf history {
      type history;
      tailf:info "History size";
    }
    leaf autowizard {
      type boolean;
      tailf:info "Automatically query user for mandatory elems";
    }
    leaf show-defaults {
      type boolean;
      tailf:info "Show default values when showing the configuration";
    }
    leaf display-level {
      type display-level;
      tailf:info "Max depth to show when displaying configuration";
    }
    leaf prompt1 {
      type string;
      tailf:info "Prompt for operational mode";
    }
    leaf prompt2 {
      type string;
      tailf:info "Prompt for configure mode";
    }
    leaf devtools {
      type boolean;
      tailf:info "Enable/disable development tools";
    }
  }

  list alias {
    nacm:default-deny-write;
    key name;
    tailf:info "Create command alias.";
    leaf name {
      type string;
      tailf:info "Name of the command alias. An alias name can be a single
                  word or multiple words joined by a dash (-).";
    }
    leaf expansion {
      type string;
      mandatory true;
      tailf:info "Original command syntax. Valid abbreviations of the original
                  command syntax can be entered for the command-syntax
                  argument.";
    }
  }
  container session {
    nacm:default-deny-write;
    uses session-params;
    presence "";
    tailf:info "Global default CLI session parameters";
  }
  list user {
    tailf:info "User specific command aliases and default CLI session
                parameters";
    nacm:default-deny-all;
    key name;
    leaf name {
      type string;
    }
    leaf description {
      type string;
      tailf:info "User description";
    }
    list alias {
      key name;
      tailf:info "Create command alias.";
      leaf name {
        type string;
        tailf:info "Name of the command alias. An alias name can be a single
                    word or multiple words joined by a dash (-).";
      }
      leaf expansion {
        type string;
        mandatory true;
        tailf:info "Original command syntax. Valid abbreviations of the original
                    command syntax can be entered for the command-syntax
                    argument.";
      }
    }
    container session {
      uses session-params;
      tailf:info "User specific default CLI session parameters";
    }
  }

}
