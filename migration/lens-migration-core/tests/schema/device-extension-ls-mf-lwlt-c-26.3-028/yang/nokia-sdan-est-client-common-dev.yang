module nokia-sdan-est-client-common-dev {

    namespace
        "http://www.nokia.com/Fixed-Networks/BBA/yang:nokia-sdan-est-client-common-dev";

    prefix nokia-sdan-est-client-common-dev;

    import nokia-sdan-est-client { prefix estc; }

  organization
    "Nokia";

  contact
    "Comments or questions about this Nokia YANG module should be
     directed to <mailto:isam.yang@nokia.com>.";

  description
    "This module contains a collection of YANG definitions for
     supporting Nokia specific requirements as applicable to its
     access network equipment.

     Specifically, this module provides restrictions (=deviations) for
     the implementation in the ISAM ?????.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

    revision 2025-09-05  {
        description "TLS Hello parameter related deviations.";
        reference "Nokia specific.";
    }

    revision 2024-08-10 {
        description "EST client related deviations";
        reference "Nokia specific.";
    }

    deviation "/estc:est-client/estc:est-certificate-profile/estc:est-server/estc:server-authentication/estc:server-auth" {
         deviate delete {
            must 'pinned-ca-certs or pinned-server-certs';
         }
    }

     deviation "/estc:est-client/estc:est-certificate-profile/estc:est-server/estc:server-authentication/estc:server-auth" {
         deviate add {
            must 'pinned-ca-certs' {
                error-message "Only 'pinned-ca-certs' supported for server authentication";
                description "Only 'pinned-ca-certs' supported for server authentication.";
            }
         }
    }

    deviation "/estc:est-client/estc:est-certificate-profile/estc:est-server/estc:server-authentication/estc:server-auth/estc:pinned-server-certs" {
        deviate not-supported;
    }
    deviation "/estc:est-client/estc:est-certificate-profile/estc:est-server/estc:server-authentication/estc:server-auth/estc:pinned-ca-certs" {
        description "Make pinned-ca-certs mandatory.";
        deviate add {
            mandatory true;
        }
    }
    deviation "/estc:est-client/estc:est-certificate-profile/estc:certificate-request-attributes/estc:explicit-provision-policy" {
        description "The duid in case of auto-fill-duid-attributes set to true together with subject-distinguished-names and subject-alternative-names are verified against generating a valid CSR request. If not, the configuration fails";
        deviate add {}
    }
    deviation "/estc:est-client/estc:est-certificate-profile/estc:est-server/estc:hello-params/estc:cipher-suites/estc:cipher-suite"
    {
       description "The YANG identifiers of the supported ciphers ordered by descending preference are the following:

         tls-aes-256-gcm-sha384
         tls-chacha20-poly1305-sha256
         tls-aes-128-gcm-sha256
         tls-ecdhe-rsa-with-aes-256-gcm-sha384
         tls-ecdhe-rsa-with-chacha20-poly1305-sha256
         tls-ecdhe-rsa-with-aes-128-gcm-sha256
         tls-ecdhe-rsa-with-aes-256-cbc-sha384
         tls-ecdhe-rsa-with-aes-256-cbc-sha
         tls-rsa-with-aes-256-gcm-sha384
         tls-rsa-with-aes-256-cbc-sha256
         tls-rsa-with-aes-256-cbc-sha
         tls-ecdhe-rsa-with-aes-128-cbc-sha256
         tls-ecdhe-rsa-with-aes-128-cbc-sha
         tls-rsa-with-aes-128-gcm-sha256
         tls-rsa-with-aes-128-cbc-sha256
         tls-rsa-with-aes-128-cbc-sha
       ";
      deviate add {}
    }
}
