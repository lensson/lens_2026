module nokia-ietf-alarms-common-dev {

  namespace "http://www.nokia.com/Fixed-Networks/BBA/yang/"
    + "nokia-ietf-alarms-common-dev";

  prefix nokia-ietf-alarms-common-dev;

  import ietf-alarms {
    prefix al;
  }

  organization
    "Nokia";

  contact
    "Comments or questions about this Nokia YANG module should be
     directed to <mailto:isam.yang@nokia.com>.";

  description
    "This module contains a collection of YANG deviations on top
     of the standard module.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

    revision 2025-10-01 {
    description
      "operational leaf-list alarm-notification->alt-resource and
       alarms->alarm-inventory->alarm-type->resource is not supported.";
    reference
      "Nokia Specific.";
  }

    revision 2023-02-13 {
    description
      "operational leaf-list alt-resource is not supported.";
    reference
      "Nokia Specific.";
  }

    revision 2022-11-16 {
    description
      "notification alarm-inventory-changed is not supported.";
    reference
      "Nokia Specific.";
  }

  revision 2021-10-27 {
    description
      "Initial revision.";
    reference
      "Nokia Specific.";
  }

/**********************************************/
/* definitions which should always be present */
/**********************************************/


  deviation "/al:alarms/al:alarm-list/al:purge-alarms" {
    description "This action is not supported currently";
    deviate not-supported;
  }

  deviation "/al:alarms/al:control/al:max-alarm-status-changes" {
    description "The configuration of these leaves are not supported currently";
    deviate not-supported;
  }
  deviation "/al:alarms/al:control/al:notify-status-changes" {
    description "The configuration of these leaves are not supported currently";
    deviate not-supported;
  }
  deviation "/al:alarms/al:control/al:notify-severity-level" {
    description "The configuration of these leaves are not supported currently";
    deviate not-supported;
  }
  deviation "/al:alarms/al:alarm-list/al:alarm/al:last-raised" {
    description "This operational leaf is not supported currently";
    deviate not-supported;
  }
  deviation "/al:alarms/al:summary/al:alarm-summary/al:cleared" {
    description "This operational leaf is not supported currently";
    deviate not-supported;
  }
  deviation "/al:alarms/al:summary/al:alarm-summary/al:not-cleared" {
    description "This operational leaf is not supported currently";
    deviate not-supported;
  }
  deviation "/al:alarm-inventory-changed" {
    description "This notification is not supported currently";
    deviate not-supported;
  }
  deviation "/al:alarms/al:alarm-list/al:alarm/al:alt-resource" {
    description "This operational leaf-list is not supported currently";
    deviate not-supported;
  }
  deviation "/al:alarm-notification/al:alt-resource" {
    description "This operational leaf-list is not supported currently";
    deviate not-supported;
  }
  deviation "/al:alarms/al:alarm-inventory/al:alarm-type/al:resource" {
    description "This operational leaf-list is not supported currently";
    deviate not-supported;
  }
}
