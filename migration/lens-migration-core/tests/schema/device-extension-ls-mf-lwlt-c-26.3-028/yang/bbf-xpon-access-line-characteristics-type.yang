module bbf-xpon-access-line-characteristics-type {
  yang-version 1.1;
  namespace "urn:bbf:yang:bbf-xpon-access-line-characteristics-type";

  prefix bbf-xpon-acc-type;

  import bbf-access-line-characteristics-base-type {
    prefix bbf-base-acc-type;
  }

  organization 
    "Broadband Forum <https://www.broadband-forum.org>
     Common YANG Work Area";

  contact
    "Comments or questions about this Broadband Forum YANG module
     should be directed to <mailto:help@broadband-forum.org>.

     Editor:      Ludwig Pauwels, Nokia

     Editor:      Joey Boyd, ADTRAN

     WA Director: Sven Ooghe, Nokia

     WA Director: Joey Boyd, ADTRAN";

  description
    "This module contains a collection of YANG definitions that
     extend the definitions for xPON access technologies and
     that are used to manage the access node xPON access line
     characteristics applied to protocol frames.

     The xPON access extensions included here are defined in the IETF
     Internet draft 'draft-lihawi-ancp-protocol-access-extension-03'.

     Copyright (c) 2019, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please  reference the Forum IPR Policy for patent licensing terms
     <https://www.broadband-forum.org/ipr-policy>.

     Any moral rights which are necessary to exercise under the above
     license grant are also deemed granted under this license.

     This version of this YANG module is part of TR-383; see
     the TR itself for full legal notices.";
     
  reference
    "IETF 'draft-lihawi-ancp-protocol-access-extension-03'";

  revision 2019-10-16 {
    description
      "Initial revision.";
    reference
      "None.";
  }

  identity xpon-access-line-attribute {
    base bbf-base-acc-type:access-line-attribute;
    description
     "Base identity for defining xPON access line attributes at the
      onu-v-vrefpoint as defined by TR-385.
      This is an abstract identity and MUST NOT be used for access
      line attributes.";
    reference
      "IETF 'draft-lihawi-ancp-protocol-access-extension-03'
       clause 6.3";
  }

  identity xpon-access-line-attribute-dhcpv4 {
    base xpon-access-line-attribute;
    description
      "Base identity for defining xpon access line attributes for
       dhcpv4 protocol";
    reference
      "IETF 'draft-lihawi-ancp-protocol-access-extension-03'
       clause 6.3";    
  }

  identity xpon-access-line-attribute-dhcpv6 {
    base xpon-access-line-attribute;
    description
      "Base identity for defining xpon access line attributes for
       dhcpv6 protocol";
    reference
      "IETF 'draft-lihawi-ancp-protocol-access-extension-03'
       clause 6.3";    
  }

  identity xpon-access-line-attribute-ancp {
    base xpon-access-line-attribute;
    description
      "Base identity for defining xpon access line attributes for
       ancp protocol";
    reference
      "IETF 'draft-lihawi-ancp-protocol-access-extension-03'
       clause 6.3";    
  }

  identity xpon-access-line-attribute-pppoe {
    base xpon-access-line-attribute;
    description
      "Base identity for defining xpon access line attributes for
       pppoe protocol";
    reference
      "IETF 'draft-lihawi-ancp-protocol-access-extension-03'
       clause 6.3";    
  }

  identity xpon-access-line-state { 
    base xpon-access-line-attribute-ancp;
    description  
      "The state of the xPON access line."; 
    reference
      "IETF 'draft-lihawi-ancp-protocol-access-extension-03' 
       clause 6.3.1";
  } 

  identity xpon-access-type { 
    base xpon-access-line-attribute-ancp;
    description  
      "The type of xPON transmission system in use."; 
    reference
      "IETF 'draft-lihawi-ancp-protocol-access-extension-03' 
       clause 6.3.2";
  } 

  identity onu-average-data-rate-downstream  { 
    base xpon-access-line-attribute-ancp;
    description  
      "The ONU downstream average data rate layer 2 at the 
      onu-v-vrefpoint as defined by TR-385."; 
    reference
      "IETF 'draft-lihawi-ancp-protocol-access-extension-03' 
       clause 6.3.3";
  } 

  identity onu-peak-data-rate-downstream  { 
    base xpon-access-line-attribute-ancp;
    base xpon-access-line-attribute-dhcpv4;
    base xpon-access-line-attribute-dhcpv6;
    base xpon-access-line-attribute-pppoe;
    description  
      "The ONU downstream peak data rate layer 2 at the 
      onu-v-vrefpoint as defined by TR-385."; 
    reference
      "IETF 'draft-lihawi-ancp-protocol-access-extension-03' 
       clause 6.3.4";
  } 

  identity onu-maximum-data-rate-upstream  { 
    base xpon-access-line-attribute-ancp;
    base xpon-access-line-attribute-dhcpv4;
    base xpon-access-line-attribute-dhcpv6;
    base xpon-access-line-attribute-pppoe;
    description  
      "The ONU upstream maximum data rate layer 2 at the 
       onu-v-vrefpoint as defined by TR-385."; 
    reference
      "IETF 'draft-lihawi-ancp-protocol-access-extension-03' 
       clause 6.3.5";
  } 

  identity onu-assured-data-rate-upstream  { 
    base xpon-access-line-attribute-ancp;
    description  
      "The ONU upstream assured data rate layer 2 at the 
      onu-v-vrefpoint as defined by TR-385."; 
    reference
      "IETF 'draft-lihawi-ancp-protocol-access-extension-03' 
       clause 6.3.6";
  } 

  identity xpon-tree-maximum-data-rate-upstream { 
    base xpon-access-line-attribute-ancp;
    base xpon-access-line-attribute-dhcpv4;
    base xpon-access-line-attribute-dhcpv6;
    base xpon-access-line-attribute-pppoe;
    description  
      "The xPON tree upstream maximum data rate layer 2 at the 
       channel termination as defined by TR-385."; 
    reference
      "IETF 'draft-lihawi-ancp-protocol-access-extension-03' 
       clause 6.3.7";  
  } 

  identity xpon-tree-maximum-data-rate-downstream { 
    base xpon-access-line-attribute-ancp;
    base xpon-access-line-attribute-dhcpv4;
    base xpon-access-line-attribute-dhcpv6;
    base xpon-access-line-attribute-pppoe;
    description  
      "The xPON tree downstream maximum data rate layer 2 at the 
       channel termination as defined by TR-385."; 
    reference
      "IETF 'draft-lihawi-ancp-protocol-access-extension-03' 
       clause 6.3.8";  
  }
}
