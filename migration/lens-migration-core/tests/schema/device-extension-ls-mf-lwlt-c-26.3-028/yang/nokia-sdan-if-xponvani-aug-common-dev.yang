module nokia-sdan-if-xponvani-aug-common-dev {

  namespace
    "http://www.nokia.com/Fixed-Networks/BBA/yang/"
  + "nokia-sdan-if-xponvani-aug-common-dev";

  prefix nokia-sdan-if-xponvani-aug-common-dev;


  import ietf-interfaces {
    prefix if;
  }

  import bbf-xponvani {
    prefix bbf-xponvani;
  }

  import nokia-sdan-if-xponvani-aug {
    prefix nokia-sdan-if-xponvani-aug;
  }

  organization
    "Nokia";

  contact
    "isam.yang@nokia.com";

  description
    "The NOKIA IETF/System YANG module supporting
     deviations on top of standard.";

  revision 2024-09-04 {
    description
      "Correct the error message.";
    reference
      "Nokia Specific.";
  }

  revision 2020-07-20 {
    description
      "Initial revision.";
    reference
      "TBD";
  }

  deviation
  "/if:interfaces/if:interface/bbf-xponvani:v-ani/nokia-sdan-if-xponvani-aug:onu-name" {
    deviate add {
    }
  }

}
