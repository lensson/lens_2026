module nokia-sdan-hierarchy-meta-info-mounted {
  yang-version 1.1;
  namespace "http://www.nokia.com/Fixed-Networks/BBA/yang/"
           + "nokia-sdan-hierarchy-meta-info-mounted";

  prefix nokia-sdan-hierarchy-meta-info-mounted;

  import bbf-fiber-onu-emulated-mount {
     prefix onu;
  }

  import ietf-interfaces-mounted {
    prefix if-mounted;
  }

  import ietf-hardware-mounted {
    prefix hw-mounted;
  }

  import ietf-system-mounted {
    prefix sys-mounted;
  }

  organization
    "Nokia";

  contact
    "Comments or questions about this Nokia YANG module should be
     directed to <mailto:isam.yang@nokia.com>.";

  description
    "This module contains a collection of YANG definitions for
     supporting Nokia specific requirements as applicable to its
     access network equipment.

     Specifically this module contains the YANG definition for the
     hierarchy meta info data for onu objects. It augments the
     interface, hardware and system model with this definition so
     that the hierarchy meta info can be configured for an interface
     or hardware component of the onu or for the onu system as a whole.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2025, Nokia. All Rights Reserved.";

  revision 2025-09-26 {
    description "Initial revision.";
    reference "Nokia specific EPIC BBN-202180.";
  }

  grouping hierarchy-meta-info-parameters {
    description
      "hierarchy-meta-info parameters to be reused for different objects.";
    leaf hierarchy-meta-info {
      type string {
        length "0..128";
      }
      description "Hierarchy meta info data.";
    }
  }

  augment "/onu:onus/onu:onu/onu:root/if-mounted:interfaces/if-mounted:interface" {
    description "Augment interface with the hierarchy meta info data.";
    uses nokia-sdan-hierarchy-meta-info-mounted:hierarchy-meta-info-parameters;
  }

  augment "/onu:onus/onu:onu/onu:root/hw-mounted:hardware/hw-mounted:component" {
    description "Augment hardware component with the hierarchy meta info data.";
    uses nokia-sdan-hierarchy-meta-info-mounted:hierarchy-meta-info-parameters;
  }

  augment "/onu:onus/onu:onu/onu:root/sys-mounted:system" {
    description "Augment system with the hierarchy meta info data.";
    uses nokia-sdan-hierarchy-meta-info-mounted:hierarchy-meta-info-parameters;
  }

}
