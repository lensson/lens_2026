module nokia-ietf-interfaces-inexpressible-constraints-validator-l2fwd-common-dev {

  yang-version "1.1";
  namespace "http://www.nokia.com/Fixed-Networks/BBA/yang/"
            + "nokia-ietf-interfaces-inexpressible-constraints-validator-l2fwd-common-dev";

  prefix nokia-ietf-interfaces-inexpressible-constraints-validator-l2fwd-common-dev;

  import ietf-interfaces {
    prefix if;
  }
  
  organization
    "NOKIA";

  contact
    "Comments or questions about this Nokia YANG module should be
     directed to <mailto:isam.yang@nokia.com>.";

  description
    "The NOKIA common/nokia-ietf-interfaces-inexpressible-constraints-validator-l2fwd-common-dev
     YANG module supporting deviations on top of ietf-ssh-server standard.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2019, Nokia. All Rights Reserved.";

  revision 2017-04-24 {
    description
      "Initial revision.";
    reference
      "Nokia specific"; 
  }

  deviation "/if:interfaces/if:interface" {
    description
      "The error message 'Number of Static MACs per vlan-sub-interface exceeds max-number-mac-addresses of the vlan-sub-interface.' will be displayed when the constraint is violated.";
    deviate add {}
  }
  
  deviation "/if:interfaces/if:interface" {
    description
      "The error message 'Number of network vlan-sub-interface exceeds maximum network vlan-sub-interfaces supported by the system/board.' will be displayed when the constraint is violated.";
    deviate add {}
  }
  
  deviation "/if:interfaces/if:interface" {
    description
      "The error message 'Number of user vlan-sub-interface exceeds maximum user vlan-sub-interfaces supported by the system/board.' will be displayed when the constraint is violated.";
    deviate add {}
  }
  
  deviation "/if:interfaces/if:interface" {
    description
      "signalling-channel and uni-name must be configured(or signalling-channel must be unconfigured) when dot1x enable(or disable) on olt-v-enet interface.
       The error message 'signalling-channel and uni-name must be configured(or signalling-channel must be unconfigured) when dot1x enable(or disable) on olt-v-enet interface:' will be displayed when the constraint is violated.";
    deviate add {}
  }
  
  deviation "/if:interfaces/if:interface" {
    description
      "Uni-name must be configured when flush mac enable on olt-v-enet interface:
       The error message 'Uni-name must be configured when flush mac enable on olt-v-enet interface:' will be displayed when the constraint is violated.";
    deviate add {}
  }
  
  deviation "/if:interfaces/if:interface" {
    description
      "Other dependent xpaths where this rule applies are:
        '/bbf-qos-pol:qos-policy-profiles/bbf-qos-pol:policy-profile'
       The error message 'allow-server-at-user-side can only be configured ' will be displayed when the constraint is violated.";
    deviate add {}
  }
  
  deviation "/if:interfaces/if:interface" {
    description
      "allow-server-at-user-side at user VSI, should be enabled for both DHCPv4 and DHCPv6 protocols together due to HW limitation.
       The error message 'allow-server-at-user-side should be enabled for both DHCPv4 and DHCPv6 together.' will be displayed when the constraint is violated.";
    deviate add {}
  }
  
}
