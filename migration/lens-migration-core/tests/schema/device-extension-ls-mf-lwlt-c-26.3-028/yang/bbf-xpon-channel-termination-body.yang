submodule bbf-xpon-channel-termination-body {
  yang-version 1.1;
  belongs-to bbf-xpon {
    prefix bbf-xpon;
  }

  import ietf-interfaces {
    prefix if;
  }
  import ietf-yang-types {
    prefix yang;
  }
  import bbf-xpon-types {
    prefix bbf-xpon-types;
  }
  import bbf-xpon-defects {
    prefix bbf-xpon-def;
  }
  include bbf-xpon-base;

  organization
    "Broadband Forum <https://www.broadband-forum.org>
     Fiber Access Networks Work Area";
  contact
    "Comments or questions about this Broadband Forum YANG module
     should be directed to <mailto:info@broadband-forum.org>.

     Editor:      Robert Peschi, Nokia

     PS Leader:   Joey Boyd, Adtran

     WA Director: Marta Seda, Calix";
  description
    "This submodule contains a collection of YANG definitions for
     managing channel terminations.

     Copyright (c) 2018-2024, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-385i3; see
     the TR itself for full legal notices.";

  revision 2024-04-23 {
    description
      "Issue 3.
       * Approval Date:    2024-04-23.
       * Publication Date: 2024-04-23.";
    reference
      "TR-385i3: YANG Modules for PON Management
               <https://www.broadband-forum.org/technical/download/
                        TR-385_Issue-3.pdf>";
  }
  revision 2023-06-21 {
    description
      "Issue 2 Amendment 1.
       * Approval Date:    2023-06-21.
       * Publication Date: 2023-06-21.";
    reference
      "TR-385i2a1: ITU-T PON YANG Modules
               <https://www.broadband-forum.org/technical/download/
                        TR-385_Issue-2_Amendment-1.pdf>";
  }
  revision 2020-10-13 {
    description
      "Issue 2.
       * Approval Date:    2020-10-13.
       * Publication Date: 2020-10-13.";
    reference
      "TR-385i2: ITU-T PON YANG Modules
               <https://www.broadband-forum.org/technical/download/
                        TR-385_Issue-2.pdf>";
  }
  revision 2019-02-25 {
    description
      "Initial revision.
       * Approval Date:    2019-02-25.
       * Publication Date: 2019-02-25.";
    reference
      "TR-385: ITU-T PON YANG Modules
               <https://www.broadband-forum.org/technical/download/
                        TR-385.pdf>";
  }

  feature onu-phase-drift-monitoring-control {
    description
      "Indicates support for the configuration of Optical Network
       Unit (ONU) phase drift monitoring.";
  }

  feature channel-termination-defects {
    description
      "Indicates support for reporting defects observed at the channel
       termination.";
  }

  feature channel-termination-defect-notifications {
    description
      "Indicates support for reporting state changes of the defects
       observed at the channel termination.";
  }

  grouping onu-phase-drift-monitoring-data {
    description
      "The arrival phase of the Optical Network Unit (ONU)
       transmission may drift due to aging, temperature changes and
       other factors. In those cases, the equalization delay can be
       recalculated/updated from the drift of the upstream
       transmission. This allows small corrections to be made without
       having to re-range the ONU.
       Configuration parameters in this grouping govern ONU
       upstream transmission phase drift monitoring by an Optical
       Line Termination (OLT).";
    reference
      "ITU-T G.984.x Clause 10.3.5;
       ITU-T G.987.x Clause 13.1.6;
       ITU-T G.989.x Clause 13.1.6;
       ITU-T G.9807.x Clause 13.1.6";
    leaf monitoring-interval {
      type union {
        type uint32 {
          range "1..max";
        }
        type enumeration {
          enum disable {
            description
              "Disable drift monitoring.";
          }
        }
      }
      units "milliseconds";
      default "1000";
      description
        "Interval in milliseconds for Optical Network Unit (ONU)
         transmission phase drift monitoring.";
      reference
        "ITU-T G.984.x Clause 10.3.5;
         ITU-T G.987.x Clause 13.1.6;
         ITU-T G.989.x Clause 13.1.6;
         ITU-T G.9807.x Clause 13.1.6";
    }
    leaf lower-threshold {
      type union {
        type uint32 {
          range "1..max";
        }
        type enumeration {
          enum itut-recommended-value {
            description
              "ITU-T recommended value (see reference).";
          }
        }
      }
      units "bits";
      default "itut-recommended-value";
      description
        "Lower threshold in bits. Drift value below this threshold
         is considered acceptable and doesn't require any corrective
         actions. If drift value averaged over monitoring-interval
         exceeds the 'lower-threshold' and doesn't exceed the
         'upper-threshold', Optical Line Termination (OLT) must
         calculate new equalization delay value and transmit it to the
         Optical Network Unit (ONU) using Tanging_Time PLOAM message.
         The OLT Channel Termination (CT) also raises a Drift of
         Window (DOWi) event.
         - US speed 2.48832 Gbps : +- 8 bits
         - US speed 9.95328 Gbps : +- 32 bits.";
      reference
        "ITU-T G.984.x Clause 10.3.5;
         ITU-T G.987.x Clause 13.1.6;
         ITU-T G.989.x Clause 13.1.6;
         ITU-T G.9807.x Clause 13.1.6";
    }
    leaf upper-threshold {
      type union {
        type uint32 {
          range "1..max";
        }
        type enumeration {
          enum itut-recommended-value {
            description
              "ITU-T recommended value (see reference).";
          }
        }
      }
      units "bits";
      default "itut-recommended-value";
      description
        "The upper threshold establishes the critical bounds beyond
         which the transmission drift can affect the other Optical
         Network Units (ONU) on the PON. If the drift exceeds the
         upper threshold, the Optical Line Termination (OLT) Channel
         Termination (CT) declares transmission interference warning
         (TIWi) and takes further mitigating actions that may include
         deactivation or disabling of the offending ONU-ID, or
         execution of a rogue Optical Network Unit (ONU) diagnostic
         procedure. The OLT CT also raises a Drift of Window (DOWi)
         event.
         - US speed 2.48832 Gbps : +- 16 bits
         - US speed 9.95328 Gbps : +- 64 bits.";
      reference
        "ITU-T G.984.x Clause 10.3.5;
         ITU-T G.987.x Clause 13.1.6;
         ITU-T G.989.x Clause 13.1.6;
         ITU-T G.9807.x Clause 13.1.6";
    }
  }

  grouping channel-termination-config-data {
    description
      "All configuration data for a channel termination.";
    leaf channel-pair-ref {
      type if:interface-ref;
      description
        "Reference to a channel pair.";
    }
    leaf channel-termination-type {
      type identityref {
        base bbf-xpon-types:channel-pair-type-base;
      }
      mandatory true;
      description
        "Represents the type of channel termination (e.g.,
         TDM 50G-PON, 25GS-PON, TWDM NG-PON2, PtP NG-PON2, XGS-PON,
         XG-PON, G-PON).";
    }
    leaf meant-for-type-b-primary-role {
      type boolean;
      description
        "If 'true', the channel termination is meant to play type B
         protection Primary role when it refers to a channel pair.
         When false, the channel termination is meant to play
         type B protection Secondary role when it refers to a
         channel pair.";
      reference
        "ITU-T G.989.3 Amd.1 Clause 18.1";
    }
    leaf fiftyg-admin-label {
      when "derived-from-or-self"
         + "(../bbf-xpon:channel-termination-type,"
         + "'bbf-xpon-types:fiftyg-twdm') or "
         + "derived-from-or-self"
         + "(../bbf-xpon:channel-termination-type,"
         + "'bbf-xpon-types:fiftyg-tdm')" {
        description
          "Only applicable when the channel termination type is
           'fiftyg-twdm' or 'fiftyg-tdm' or derived from either.";
      }
      type uint32 {
        range "0..268435455" {
          description
            "0 to 2^28-1.";
        }
      }
      description
        "For 50G-PON, the admin-label is configurable and is
         28 bits long. It is the configurable part of the PON
         Identifier (PON-ID) which is available as state data.";
      reference
        "ITU-T G.9804.2 Clause 6.5.2.2";
    }
    leaf twentyfivegs-pon-id {
      when "derived-from-or-self"
         + "(../bbf-xpon:channel-termination-type,"
         + "'bbf-xpon-types:twentyfivegs')";
      type uint32;
      description
        "For 25GS-PON, the PON Identifier (PON-ID) is entirely
         configurable and is 32 bits long. The PON-ID is also
         available as state data.";
      reference
        "MSA 25GS-PON Section 2";
    }
    leaf ngpon2-twdm-admin-label {
      when "derived-from-or-self"
         + "(../bbf-xpon:channel-termination-type,"
         + "'bbf-xpon-types:ngpon2-twdm')" {
        description
          "Only applicable for Time Wavelength Division
           Multiplexing (TWDM) NG-PON2 channel pairs.";
      }
      type uint32 {
        range "0..268435455" {
          description
            "0 to 2^28-1.";
        }
      }
      description
        "For TWDM NG-PON2, the admin-label is configurable and is
         28 bits long. It is the configurable part of the PON
         Identifier (PON-ID) which is available as state data.";
      reference
        "ITU-T G.989.3 Clause 6.1.5.3";
    }
    leaf ngpon2-ptp-admin-label {
      when "derived-from-or-self"
         + "(../bbf-xpon:channel-termination-type,"
         + "'bbf-xpon-types:ngpon2-ptp')" {
        description
          "Only applicable for Point-to-Point (PtP) NG-PON2
           channel pairs.";
      }
      type uint32 {
        range "0..4194303" {
          description
            "0 to 2^22-1.";
        }
      }
      description
        "For PtP NG-PON2, the admin-label is configurable and is
         22 bits long. It is the configurable part of the PON
         Identifier (PON-ID) which is available as state data.";
      reference
        "ITU-T G.989.3 Clause 6.1.5.3";
    }
    leaf xgs-pon-id {
      when "derived-from-or-self"
         + "(../bbf-xpon:channel-termination-type,"
         + "'bbf-xpon-types:xgs')" {
        description
          "Only applicable for XGS-PON channel pairs.";
      }
      type uint32;
      description
        "For XGS-PON, the PON Identifier (PON-ID) is entirely
         configurable and is 32 bits long. The PON-ID is also
         available as state data.";
      reference
        "ITU-T G.9807.1 Clause C.10.1.1.1.3";
    }
    leaf xgpon-pon-id {
      when "derived-from-or-self"
         + "(../bbf-xpon:channel-termination-type,"
         + "'bbf-xpon-types:xgpon')" {
        description
          "Only applicable for XG-PON channel pairs.";
      }
      type uint32;
      description
        "For XG-PON, the PON Identifier (PON-ID) is entirely
         configurable and is 32 bits long. The PON-ID is also
         available as state data.";
      reference
        "ITU-T G.987.3 Clause E.2";
    }
    leaf gpon-pon-id {
      when "derived-from-or-self"
         + "(../bbf-xpon:channel-termination-type,"
         + "'bbf-xpon-types:gpon')" {
        description
          "Only applicable for G-PON channel pairs.";
      }
      type bbf-xpon-types:string-hex14;
      description
        "For G-PON, the PON Identifier (PON-ID) is entirely
         configurable with any binary value over 7 bytes. The PON-ID
         is also available as state data.";
      reference
        "ITU-T G.984.3 Clause C.2.2";
    }
    leaf pon-tag {
      when "not(derived-from-or-self"
         + "(../bbf-xpon:channel-termination-type,"
         + "'bbf-xpon-types:gpon'))" {
        description
          "Not applicable for G-PON channel pairs.";
      }
      type string {
        pattern '[0-9a-fA-F]{16}';
      }
      description
        "8 bytes. Each octet is represented by two hex values.
         Used to specify channel-pair-TAG attribute in 25GS-PON,
         NG-PON2, XGS-PON and XG-PON downstream PLOAM messages.
         The 'pon-tag' is not applicable for G-PON.";
    }
    leaf ber-calc-period {
      type uint32 {
        range "1..864000";
      }
      units "0.1 seconds";
      default "10";
      description
        "Measurement period used to determine if a Signal Degrade
         (SDi) alarm has occurred for an Optical Network Unit (ONU).";
      reference
        "ITU-T G.984.3 Clause 11.1.3";
    }
    leaf location {
      type identityref {
        base bbf-xpon-types:location-base;
      }
      description
        "Indicates whether the Channel Termination (CT) is physically
         inside the Optical Line Termination (OLT) i.e., can be
         related to a port in the OLT hardware model or physically
         part of another OLT.";
    }
    container onu-phase-drift-monitoring-control {
      if-feature "bbf-xpon:onu-phase-drift-monitoring-control";
      uses onu-phase-drift-monitoring-data;
      description
        "Optical Network Unit (ONU) Phase Drift monitoring
         configuration.";
    }
    leaf-list notifiable-defect {
      if-feature "bbf-xpon:channel-termination-defect-notifications";
      type identityref {
        base bbf-xpon-def:items-detected-at-olt-for-ct;
      }
      description
        "Optical Line Termination (OLT) is expected to generate a
         'defect-state-change' notification each time defect(s)
         listed in this leaf-list are raised or cleared.
         If 'notifiable-defect' includes an identity which
         is the base value for other defect(s) identity(ies),
         the OLT will generate a single notification when status of
         any defect derived from this base value changes.

         In case the leaf-list is empty (as by default) the OLT
         should not generate any 'defect-state-change'
         notification.";
    }
  }

  grouping channel-termination-oper-data {
    description
      "All oper data for a channel termination.";
    leaf pon-id-display {
      type bbf-xpon-types:pon-id-display-type;
      description
        "The PON Identifier (PON-ID) of the channel termination.
         Per ITU-T G.989.3, ITU-T G.9807.1, ITU-T G.987.3,
         ITU-T G.984.3, and ITU-T G.9804.2, depending of the
         xPON type some part of this object is configured by
         the operator and the other part is genuine operational
         data determined by the system.";
    }
    leaf type-b-state {
      type identityref {
        base bbf-xpon-types:type-b-state-base;
      }
      description
        "The type B protection state of the Channel Termination (CT);
         it will typically be active/standby. When the channel
         termination is not yet referring to a channel pair, it is not
         part of any type B protection scheme (and not usable either);
         in that case its type-b-state has the value
         'not-part-of-type-b.";
      reference
        "ITU-T G.989.3 Amd.2 Clause 18.2";
    }
    leaf location {
      type identityref {
        base bbf-xpon-types:location-base;
      }
      description
        "Indicates whether the Channel Termination (CT) is physically
         inside the Optical Line Termination (OLT) i.e., can be
         related to a port in the OLT hardware model or physically
         part of another OLT.";
    }
    leaf-list active-defects {
      if-feature "bbf-xpon:channel-termination-defects";
      type identityref {
        base bbf-xpon-def:items-detected-at-olt-for-ct;
      }
      description
        "Defects detected by Optical Line Termination (OLT) for
         Channel Termination (CT).

         All applicable identities should be provided as value.";
      reference
        "ITU-T G.984.3 Clause 11.1.1;
         ITU-T G.987.3 Clause 14.2.1;
         ITU-T G.989.3 Amd.2 Table 14-2;
         ITU-T G.9807.1 Amd.1 Table C.14.2";
    }
    leaf-list sufi-affected-onus {
      if-feature "bbf-xpon:channel-termination-defects";
      type bbf-xpon-types:onu-serial-number;
      description
        "List of Optical Network Units (ONU) that have exhibited a
         start-up failure (SUFi).";
      reference
        "ITU-T G.984.3 Clause 11.1.1 - SUFi;
         ITU-T G.987.3 Clause 14.2.1 - SUFi;
         ITU-T G.989.3 Amd.2 Table 14-2 - SUFi;
         ITU-T G.9807.1 Amd.1 Table C.14.2 - SUFi";
    }
    notification defect-state-change {
      if-feature "bbf-xpon:channel-termination-defect-notifications";
      description
        "A notification traceable to a channel-termination which
         signifies that defect(s) detected by an Optical Line
         Termination (OLT) have been raised and/or cleared. Such
         notification is only generated for defects listed in the
         'notifiable-defect' leaf list.";
      list defect {
        key "type";
        description
          "A notifiable defect that has changed state since
           the previous 'defect-state-change' notification.";
        leaf type {
          type identityref {
            base bbf-xpon-def:items-detected-at-olt-for-ct;
          }
          description
            "Defect type.";
        }
        leaf state {
          type bbf-xpon-def:defect-state;
          mandatory true;
          description
            "The current defect state.";
        }
        leaf last-change {
          type yang:date-and-time;
          mandatory true;
          description
            "The Optical Line Termination (OLT) system date and
             time when the OLT has declared that the defect state
             has changed.";
        }
      }
    }
  }

  augment "/if:interfaces/if:interface/bbf-xpon:channel-termination" {
    when "../if:type = 'bbf-xponift:channel-termination'";
    description
      "Configuration of an xPON channel termination.";
    uses channel-termination-config-data;
  }

  augment "/if:interfaces-state/if:interface/bbf-xpon:channel-"
        + "termination" {
    description
      "State data of an xPON channel termination.";
    uses channel-termination-oper-data;
  }
}
