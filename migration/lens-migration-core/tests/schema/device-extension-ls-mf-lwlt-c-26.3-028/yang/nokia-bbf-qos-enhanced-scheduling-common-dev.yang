module nokia-bbf-qos-enhanced-scheduling-common-dev {

  namespace
    "http://www.nokia.com/Fixed-Networks/BBA/yang/nokia-bbf-qos-enhanced-scheduling-common-dev";

  prefix  nokia-bbf-qos-enhanced-scheduling-common-dev;

  import ietf-interfaces {
    prefix if;
  }

  import bbf-if-type {
    prefix bbfift;
  }

  import bbf-qos-enhanced-scheduling{
    prefix bbf-qos-sched;
  }

  import bbf-qos-traffic-mngt {
    prefix bbf-qos-tm;
  }
  
  import bbf-xpon-if-type {
    prefix bbf-xponift;
  }

  import nokia-yang-types {
    prefix "nok-typ";
  }


  organization
    "Nokia";

  contact
    "isam.yang@nokia.com";

  description
    "This module contains a collection of YANG deviations on top 
     of standard for supporting BBF/bbf-qos-policies YANG module.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2017-2018, Nokia. All Rights Reserved.";

  /* revision */
  revision 2025-03-28 {
    description
      "Adjust tm L1 scheduler-node number check.";
    reference
      "Nokia specific";
  }

  revision 2024-06-17 {
    description
      "Set dimenson of L1 scheduler-node instances(128).";
    reference
      "Nokia specific";
  }

  revision 2023-03-22 {
    description
      "Initial revision.";
    reference
      "Nokia specific";
  }
  
  revision 2022-11-23 {
    description
      "Initial revision.";
    reference
      "Nokia specific";
  }
    
  revision 2019-08-14 {
    description
      "Add other check after modify legacy atc cases.";
    reference
      "Nokia specific";
  }
  
  revision 2019-03-27 {
    description
      "Add deviation for hqos.";
    reference
      "Nokia specific";
  }

  /* COMMENTED FOR CREATE PERFORMANCE
  deviation "/if:interfaces/if:interface/bbf-qos-tm:tm-root/bbf-qos-tm:children-type/bbf-qos-sched:scheduler-node/bbf-qos-sched:scheduler-node/bbf-qos-sched:children-type/bbf-qos-sched:scheduler-node/bbf-qos-sched:child-scheduler-nodes/bbf-qos-sched:name"
  {
    deviate add {
       must "(count(current()/../../../bbf-qos-sched:scheduler-node/bbf-qos-sched:child-scheduler-nodes[bbf-qos-sched:name = current()]) + count(current()/../../../bbf-qos-sched:child-scheduler-nodes[bbf-qos-sched:name = current()])) = 1" 
       {
           error-message "One scheduler node can only have a parent node.";
       }

       must "count(current()/../../../bbf-qos-sched:scheduler-node/bbf-qos-sched:child-scheduler-nodes[bbf-qos-sched:name = current()/../../bbf-qos-sched:name]) = 0"
       {
           error-message "If a sheduler node is CSNL member of another scheduler node, this scheduer node only can contain queues.";
       }
    }
  }
  
  
  deviation "/if:interfaces/if:interface/bbf-qos-sched:egress-tm-objects/bbf-qos-sched:select-tm-objects-method/bbf-qos-sched:scheduler/bbf-qos-sched:scheduler-node-name"
  {
    deviate add {
       must "count(/if:interfaces/if:interface[if:name = current()/../bbf-qos-sched:root-if-name]/bbf-qos-tm:tm-root/bbf-qos-sched:scheduler-node[bbf-qos-sched:name = current()]/bbf-qos-sched:queue) > 0"
       {
           error-message "It is not allow to link scheduler node with empty queue-list to VSI or olt-v-enet.";
       }

       must "count(/if:interfaces/if:interface[if:name = current()/../bbf-qos-sched:root-if-name]/bbf-qos-tm:tm-root/bbf-qos-sched:child-scheduler-nodes[bbf-qos-sched:name = current()]) > 0 or count(/if:interfaces/if:interface[if:name = current()/../bbf-qos-sched:root-if-name]/bbf-qos-tm:tm-root/bbf-qos-sched:child-scheduler-nodes[bbf-qos-sched:name = /if:interfaces/if:interface[if:name = current()/../bbf-qos-sched:root-if-name]/bbf-qos-tm:tm-root/bbf-qos-sched:scheduler-node/bbf-qos-sched:child-scheduler-nodes[bbf-qos-sched:name = current()]/../bbf-qos-sched:name]) > 0"
       {
           error-message "When link scheduler-node to VSI or olt-v-enet, this node or its parent node must be CSNL member of channel-partition.";
       }
    }
  }
  */
  
  deviation "/if:interfaces/if:interface/bbf-qos-tm:tm-root/bbf-qos-tm:children-type/bbf-qos-sched:scheduler-node/bbf-qos-sched:scheduler-node"{
    deviate add {
       must "current()/../../if:type = 'bbf-xponift:channel-partition'" {
         error-message "Only channel-partition type interface can configure tm-root.";
       }
    }
  }

  deviation "/if:interfaces/if:interface/bbf-qos-sched:egress-tm-objects"{
    deviate add {
       must "current()/../if:type = 'bbfift:vlan-sub-interface' or current()/../if:type = 'bbf-xponift:olt-v-enet'" {
         error-message "Only vlan-subinterface or olt-v-enet type interface can configure egress-tm-object.";
       }
    }
  }
  
  deviation "/if:interfaces/if:interface/bbf-qos-tm:tm-root/bbf-qos-tm:children-type/bbf-qos-sched:scheduler-node/bbf-qos-sched:child-scheduler-nodes"{
    deviate add {
       must "current()/../../if:type = 'bbf-xponift:channel-partition'" {
         error-message "Only channel-partition type interface can configure tm-root.";
       }
    }
  }
  
  deviation "/if:interfaces/if:interface/bbf-qos-tm:tm-root/bbf-qos-tm:children-type/bbf-qos-sched:scheduler-node/bbf-qos-sched:child-scheduler-nodes/bbf-qos-sched:scheduling-type/bbf-qos-sched:inline/bbf-qos-sched:priority"{
    deviate replace {
    type uint32 {
      range "0";
     }
    }
  }

  deviation "/if:interfaces/if:interface/bbf-qos-tm:tm-root/bbf-qos-tm:children-type/bbf-qos-sched:scheduler-node/bbf-qos-sched:scheduler-node/bbf-qos-sched:children-type/bbf-qos-sched:scheduler-node/bbf-qos-sched:child-scheduler-nodes/bbf-qos-sched:scheduling-type/bbf-qos-sched:inline/bbf-qos-sched:priority"{
    deviate replace {
    type uint32 {
      range "0";
     }
    }
  }

  deviation "/if:interfaces/if:interface/bbf-qos-tm:tm-root/bbf-qos-tm:children-type/bbf-qos-sched:scheduler-node/bbf-qos-sched:scheduler-node/bbf-qos-sched:children-type/bbf-qos-sched:scheduler-node/bbf-qos-sched:child-scheduler-nodes"{
    deviate add {
      max-elements 32;
    }
  }

  deviation "/if:interfaces/if:interface/bbf-qos-tm:tm-root/bbf-qos-tm:children-type/bbf-qos-sched:scheduler-node/bbf-qos-sched:scheduler-node/bbf-qos-sched:children-type/bbf-qos-sched:queue/bbf-qos-sched:queue/bbf-qos-sched:pre-emption" {
    deviate not-supported;
  }
  
  
  
 deviation "/if:interfaces/if:interface/bbf-qos-tm:tm-root/bbf-qos-tm:children-type/bbf-qos-sched:scheduler-node/bbf-qos-sched:scheduler-node/bbf-qos-sched:name" {
  deviate replace {
      type nok-typ:nokia-string-ascii100;
    }
 }


}
