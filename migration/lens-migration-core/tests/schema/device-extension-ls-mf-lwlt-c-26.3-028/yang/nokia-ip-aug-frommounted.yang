module nokia-ip-aug-frommounted {
  yang-version 1.1;

  namespace "urn:ietf:params:xml:ns:yang:nokia-ip-aug-frommounted"; 

  prefix ip-aug-frommounted;
    
  
  import ietf-interfaces-frommounted {
    prefix if-frommounted;
  }
  
  import bbf-fiber-onu-emulated-mount {
    prefix onu;
  }
  
  import ietf-ip-frommounted {
    prefix ip-frommounted;
  }  
  
  import ietf-inet-types {
   prefix inet;
  } 
  

  organization
    "Nokia";

  contact
    "Comments or questions about this Nokia YANG module should be 
     directed to <mailto:isam.mibsupport@nokia.com>.";

  description
    "This module contains a collection of YANG definitions for 
     supporting Nokia specific requirements as applicable to its 
     access network equipment.
     
     Specifically, this module augments ???????.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these 
     products and to withdraw any or all of them at any future time.

     Copyright (C) 2017, Nokia. All Rights Reserved.";

  revision 2024-05-27 {
    description
      "robust configure DSCP value and sip-uni-suppl-services-profile";
    reference
      "Sub-task BBN-214388";
  }

  revision 2024-01-16 {
    description
      "Remove IPV4 node from non-iphost interface";
    reference
      "Sub-task BBN-181720";
  }

  revision 2021-07-06 {
    description
      "Change feature name from 'onu-ip-host' to 'ip-host'";
    reference
      "Nokia specific";
  }

  revision 2020-04-21 {
    description
      "Add ip-if-identification container and ip-diagnose-control container under
      interfaces/interface. Add ip-address-acquisition-method container under
      interfaces/interface/ipv4/address. Add ip-other-network-parameters
      container under interfaces-state/interface/ipv4/address";
    reference
      "Nokia specific";
  }

  revision 2019-11-18 {
    description
      "Moved ipif-lower-layer container out of ipv4 container to make it
       common to both ipv4 and ipv6 and added a leaf tag-ip-intf to
       tag inband interface";
    reference
      "Nokia specific";
  }

  revision 2017-08-01 {
    description
      "Initial revision.
       * Approval Date:    see revision date above.
       * Publication Date: yyyy-mm-dd.";
    reference
      "Nokia specific";
  }

  augment "/onu:onus/onu:onu/onu:fromroot/if-frommounted:interfaces/if-frommounted:interface" {
    description "augmnet interface ip forward with lower layer";
    container ipif-lower-layer {
      presence
        "This leaves provides the lower layer within the interface stack";

      description
        "Link ip interface to a lower layer network-port sub-interface";

      leaf sub-interface {
         type string;
          description
            "References the lower layer interface";
      }
    }
	  
      container ip-diagnose-control{
	    presence "Ip diagnose control";
	    description "Ip diagnose control";
		leaf respond-to-pings {
					type boolean;
					description
				     "If the leaf is set to ture, the interface will respond to pings";
		}
		leaf respond-to-traceroute-messages {
					type boolean;
					description
				     "If the leaf is set to ture, the interface will respond to traceroute messages";
		}			        
     }
  }

  augment "/onu:onus/onu:onu/onu:fromroot/if-frommounted:interfaces/if-frommounted:interface/ip-frommounted:ipv4" {
    description
      "Augment ipv4 with ipForwarding";

    container ip-address-acquisition-method{
      presence "Ip address acquisition method";
      description "Ip address acquisition method";
      leaf origin {
        type enumeration {
          enum static {
            description
              "Indicates that the address has been statically configured.";
          }
          enum dhcp {
            description
              "Indicates an address that has been assigned to this system by a DHCP server.";
          }
        }        
        description
          "The leaf is used to set the ip address acquisition
           method for the interface";
      }
    }

    container dhcp {
      presence "This leaves provides dhcp client specific data";
      description "This leaves provides dhcp client specific data";
      leaf dscp-mark {
        type inet:dscp;
        description
          "The differentiated service code point for outgoing DHCP message.";
      }
    }
  }
 
}
