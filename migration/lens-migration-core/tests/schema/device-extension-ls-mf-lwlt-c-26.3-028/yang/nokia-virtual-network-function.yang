module nokia-virtual-network-function {
  namespace "http://www.nokia.com/Fixed-Networks/BBA/yang/"
          + "nokia-virtual-network-function";

  prefix "nokia-vnf";

  import ietf-inet-types {
    prefix inet;
  }

  organization
    "Nokia";

  contact
    "Comments or questions about this Nokia YANG module should be 
     directed to <mailto:isam.yang@nokia.com>.";

  description
    "This module contains a collection of YANG definitions for 
     supporting Nokia specific requirements as applicable to its 
     access network equipment.
     
     Specifically, this module augments the interface model with data
     specific for the classification and processing of Layer 2 Control
     Protocol (L2CP) frames.

     This specification is published by Nokia under Non-Disclosure
     Agreement(s) (NDA) with specific parties and has to be considered
     as Confidential Information as defined in such NDA. Nokia 
     reserves the right to revise this document for any reason, 
     including but not limited to conformity with standards 
     promulgated by various agencies, utilisation of advances in the 
     state of the technical areas, or the reflection of changes in the
     design of any equipment, techniques, or procedures described or 
     referred to herein.

     The product specifications and other technical or performance 
     information contained herein are subject to change without 
     notice. Updates of this document will be issued under the above 
     NDA's.

     Nokia makes no representation or warranty, expressed or implied,
     with respect to the sufficiency, accuracy, or utility of any 
     information or opinion contained herein. Nokia expressly advises 
     that any use of for any purpose or reliance upon this technical 
     reference is at the risk of the user and that Nokia shall not be 
     liable for any damage or injury incurred by any person arising 
     out of the sufficiency, accuracy, or utility of any information 
     or opinion contained herein.

     This document is not to be construed as a suggestion to any 
     manufacturer to modify or change any of its products, nor does 
     this document represent any commitment by Nokia to sell or 
     purchase any product. Nothing contained herein shall be construed
     as conferring by implication, estoppel, or otherwise any license 
     or right under any patent, whether or not the use of any 
     information herein necessarily employs an invention of any 
     existing or later issued patent.

     Nokia reserves the right not to offer any or all of these
     products and to withdraw any or all of them at any future time.

     Copyright (C) 2018, Nokia. All Rights Reserved.";

  revision "2018-06-14" {
    description
      "Align template / pyang --lint";
    reference
      "Nokia specific";
  }

  revision "2018-05-21" {
    description
      "Initial revision.";
    reference
      "Nokia specific";
  }

  container virtual-network-functions {
      description
        "virtual network functions container";

    list virtual-network-function {
      key name;

      description
        "virtual network functions";

      leaf name {
        type string {
          length "1..64";
          pattern '[0-9a-zA-Z -]*';
        }
        description
          "A name for the virtual network function.";
      }

      leaf type {
        type string {
          length "1..32";
          pattern '[0-9a-zA-Z-]*';
        }
        description
          "A type of the virtual network function.";
      }

      leaf address {
        type inet:uri;
        description
          "The URI to connect to.";
      }

      // TODO link to certificates

      // TODO list with links to resources

   } // list virtual-network-function
  }
}
