module nokia-ipv4-address-spoofing-prevention-ipv4-antispoofing-fiber-dev {
  yang-version 1.1;

  namespace "http://www.nokia.com/Fixed-Networks/BBA/yang/"
          + "nokia-ipv4-address-spoofing-prevention-ipv4-antispoofing-fiber-dev";

  prefix nokia-ipv4-address-spoofing-prevention-ipv4-antispoofing-fiber-dev;

  import ietf-interfaces {
    prefix if;
  }

  import nokia-ipv4-address-spoofing-prevention {
    prefix nokia-ipv4-sppr;
  }
  
  import bbf-vlan-sub-interface-vector {
    prefix bbf-vsi-vctr;
  }
  
  import bbf-vlan-sub-interface-vector-usage {
    prefix bbf-vsi-vctr-usg;
  }
  
  import bbf-if-type {
    prefix bbfift;
  }
  
  import bbf-interface-usage {
    prefix bbf-if-usg;
  }
  import nokia-vlan-sub-interface-vector-ipv4-address-spoofing-prevention {
	prefix nokia-vector-ipv4-sppr;
  }


  organization
    "Nokia";

  contact
    "Comments or questions about this Nokia YANG module should be
     directed to <mailto:isam.yang@nokia.com>.";

  description
    "This module contains a collection of YANG definitions for
     supporting Nokia specific requirements as applicable to its
     access network equipment.

     Specifically, this module provides restrictions (=deviations) for
     the implementation in the ISAM ?????.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2018, Nokia. All Rights Reserved.";

  revision 2020-12-03 {
    description
      "Initial revision.";
    reference
      "Nokia specific";
  }

  deviation "/if:interfaces/nokia-ipv4-sppr:ipv4-security-statistics"
           +"/nokia-ipv4-sppr:interface/nokia-ipv4-sppr:name"  {
    deviate add {
    }
  }

  deviation "/nokia-ipv4-sppr:ipv4-antispoofing-system"
            +"/nokia-ipv4-sppr:clear-dhcp-learned-ips-on-operdown"
  {

     description
             "indicated that clear-dhcp-learned-ips-on-operdown not supported";
     deviate not-supported;

  }
 
  deviation "/if:interfaces/if:interface/nokia-ipv4-sppr:ipv4-security"
            +"/nokia-ipv4-sppr:prevent-ipv4-address-spoofing"
  {
     description
         "To remove default value false from leaf prevent-ipv4-address-spoofing on fiber platform";
     deviate delete {
        default "false";
     }
  }

  deviation "/if:interfaces/if:interface/nokia-ipv4-sppr:ipv4-security/nokia-ipv4-sppr:address" {
      deviate add {
        must "((current()/../nokia-ipv4-sppr:prevent-ipv4-address-spoofing = 'true'))" {
              error-message "Before create ipaddress,prevent-ipv4-address-spoofing should be enabled;
              Before disable prevent-ipv4-address-spoofing, ipaddress should be deleted";
              description "Before create ipaddress,prevent-ipv4-address-spoofing should be enabled";
          }
      }
  }
  deviation "/if:interfaces/if:interface/nokia-ipv4-sppr:ipv4-security" {
      deviate add {
	    must "derived-from-or-self(current()/../if:type, 'bbfift:vlan-sub-interface')"
		+" and "
		+"(current()/../bbf-if-usg:interface-usage/bbf-if-usg:"
		+"interface-usage = 'user-port'"
		+" or "
		+"current()/../bbf-if-usg:interface-usage/bbf-if-usg:"
		+"interface-usage = 'inherit'" 
		+" or "
		+"/bbf-vsi-vctr:vsi-vector-profiles/bbf-vsi-vctr:vsi-vector-profile[bbf-vsi-vctr:name=current()/../bbf-vsi-vctr:vector-profile]/"
		+"bbf-vsi-vctr-usg:interface-usage/bbf-vsi-vctr-usg:interface-usage = 'user-port')" {
          error-message "interface-usage must be user-port or inherit.";
           
          description
            "Can not enable IP address security on a VLAN 
             sub-interface that is not connected to a forwarder or multicast-vpn.";
        }
      }
   }   

}
