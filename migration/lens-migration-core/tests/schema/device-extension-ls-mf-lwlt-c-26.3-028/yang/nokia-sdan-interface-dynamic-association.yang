module nokia-sdan-interface-dynamic-association {
  yang-version 1.1;
  namespace "urn:bbf:yang:nokia-sdan-interface-dynamic-association";
  prefix nokia-itf-dyn;

  import ietf-interfaces {
    prefix if;
  }
  import bbf-if-type {
    prefix bbfift;
  }
  import nokia-sdan-interface-dynamic-association-identities {
    prefix nokia-itf-dyn-id;
  }
  import bbf-l2-forwarding {
    prefix bbf-l2-fwd;
  }
  import bbf-qos-policies {
      prefix bbf-qos-pol;
  }

  import bbf-mgmd {
      prefix bbf-mgmd;
  }
 
  organization
     "Nokia";
  contact
    "Comments or questions about this Nokia YANG module should be
     directed to <mailto:isam.yang@nokia.com>.";

  description
    "This module contains a collection of YANG definitions for
     supporting the requirements of allowing dynamic association
     between Interface to forwarder and QoS policy profile.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2024, Nokia. All Rights Reserved.";

  revision 2024-11-29 {
    description
       "description changes";
    reference
       "Nokia specific";
  }

  revision 2024-03-07 {
    description
      "Initial Revision";
    reference
      "Nokia specific";
  }

  augment "/if:interfaces/if:interface" {
    
    description
      "Data defining the association of a VLAN sub-interface to an
       l2-forwarder and QoS policy profile";

    container l2-forwarder-dynamic-association {
      presence
        "The presence of this container indicates that the
         association of the sub-interface to an l2-forwarder
         dynamically is controlled by the enclosed configuration.";
      description
        "Control the association of a sub-interface to an
         l2-forwarder.";

      leaf association-control {
        type identityref {
            base nokia-itf-dyn-id:dynamic-association-control-base;
        }

        mandatory true;
        description
          "Control the way in which the dynamic association needs
           to be handled.";
      }
    }

    container qos-policy-dynamic-association {
      when "(../nokia-itf-dyn:l2-forwarder-dynamic-association
             /association-control =
             'nokia-itf-dyn-id:only-dynamic-association-allowed')" {
        description
          "An Interface configured with l2-forwarder-dynamic-association can
           only have QoS policy dynamic association";
      }
      presence
        "The presence of this container indicates the dynamic
         association of the QoS policy profile to an Interface";

      description
        "Controls the dynamic association of Interface to the
         QoS policy profile";

      leaf association-control {
        type identityref {
          base nokia-itf-dyn-id:dynamic-association-control-base;
        }

        must "(count(../../bbf-qos-pol:ingress-qos-policy-profile) < 1) and
              (count(../../bbf-qos-pol:egress-qos-policy-profile) < 1)" {

          error-message
            "An interface enabled for dynamic QoS policy assignment cannot"
             + " have a statically provisioned QoS policy profile";

          description
            "An interface enabled with dynamic QoS Policy assignment cannot
            have a statically provisioned QoS Policy profile and it must have
            dynamic forwarder association configured.";
        }
        mandatory true;
        description
          "Indicates the dynamic association of QoS policy profile to
           an Interface.";
      }
    }
  }

  augment "/if:interfaces-state/if:interface" {
    description
      "Augment the interface-state of VLAN sub-interface with
       reference to its attached forwarder";

    container forwarder-association {
      when
        "derived-from-or-self(current()/../if:type, 'bbfift:vlan-sub-interface') or
         derived-from-or-self(current()/../if:type, 'bbfift:l2-termination')" {
        description
          "Interfaces that can be associated with a forwarder.";
      }

      description
        "This container groups the details about the forwarder
         association of this VLAN sub-interface.";
      leaf associated-forwarder {
        type bbf-l2-fwd:forwarder-state-ref;
        description
          "This leaf references the forwarder that this VLAN
           sub-interface is associated to.";
      }
      leaf association-origin {
        type identityref {
          base nokia-itf-dyn-id:association-origin-base;
        }
        description
          "This leaf indicates the origin of the association.
           The forwarder can get associated statically or
           dynamically.";
      }
    }

    container qos-policy-association {
      when
        "derived-from-or-self(current()/../if:type, 'bbfift:vlan-sub-interface')" {
        description
          "Interface(s) that can have QoS policy profiles assigned.";
      }

      description
        "This container contains details about the QoS policy
         profile association to the Interface";

      leaf associated-ingress-qos-policy {
        type bbf-qos-pol:qos-policy-profile-ref;
        description
          "This leaf references the Ingress QoS policy associated
           with this Interface.";
      }

      leaf associated-egress-qos-policy {
        type bbf-qos-pol:qos-policy-profile-ref;
        description
          "This leaf references the Egress QoS policy associated
           with this Interface.";
      }

      leaf association-origin {
        type identityref {
          base nokia-itf-dyn-id:association-origin-base;
        }
        description
          "This leaf indicates the origin of the association.
           The QoS policy profile can get associated statically or
           dynamically.";
      }
    }
  }
}
