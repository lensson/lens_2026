module nokia-ipv6-address-spoofing-prevention-common-dev {

  namespace "http://www.nokia.com/Fixed-Networks/BBA/yang/"
          + "nokia-ipv6-address-spoofing-prevention-common-dev";

  prefix nokia-ipv6-address-spoofing-prevention-common-dev;

  import ietf-interfaces {
    prefix if;
  }

  import nokia-ipv6-address-spoofing-prevention {
    prefix nokia-ipv6-sppr;
  }

  organization
    "Nokia";

  contact
    "Comments or questions about this Nokia YANG module should be
     directed to <mailto:isam.yang@nokia.com>.";

  description
    "This module contains a collection of YANG definitions for
     supporting Nokia specific requirements as applicable to its
     access network equipment.

     Specifically, this module provides restrictions (=deviations) for
     the implementation in the ISAM ?????.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2021, Nokia. All Rights Reserved.";

  revision 2021-06-16 {
    description
      "Initial revision.";
    reference
      "Nokia specific.";
  }
  
  deviation "/if:interfaces/if:interface/nokia-ipv6-sppr:ipv6-security"
           +"/nokia-ipv6-sppr:static-ipv6-address/nokia-ipv6-sppr:ip"  {
    description "ipv6-security: Static IPv6 address should be unique within a forwarder to avoid malicious user. The error-message: Static IPv6 address shall not conflict within a forwarder";
    deviate add{}
  }

  deviation "/if:interfaces/if:interface/nokia-ipv6-sppr:ipv6-security"
           +"/nokia-ipv6-sppr:static-ipv6-address/nokia-ipv6-sppr:ip"  {
    description "ipv6-security: There is a dimension based on the system resource, so that the number of static IPv6 address shall be configured within the dimension. The error-message: System maximum dimensioning limit is reached to configure static IPv6 address";
    deviate add{}
  }

  deviation "/if:interfaces/if:interface/nokia-ipv6-sppr:ipv6-security/nokia-ipv6-sppr:static-ipv6-address"  {
    deviate add{
    }
  }

  deviation "/if:interfaces/if:interface/nokia-ipv6-sppr:ipv6-security"
            +"/nokia-ipv6-sppr:static-ipv6-address" {
    deviate add {
    }
  }

  deviation "/if:interfaces/if:interface/nokia-ipv6-sppr:ipv6-security"
           +"/nokia-ipv6-sppr:static-ipv6-address/nokia-ipv6-sppr:ip"  {
    description "ipv6-security: Global Unicast IPv6 address range are allowed to configure as static IPv6 address. The error-message: The configured IPv6 address is not in Global Unicast IPv6 address range";
    deviate add{}
  }
}
