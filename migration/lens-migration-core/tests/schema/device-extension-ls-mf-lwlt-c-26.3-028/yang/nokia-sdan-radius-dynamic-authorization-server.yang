module nokia-sdan-radius-dynamic-authorization-server {
  yang-version 1.1;
  namespace "http://www.nokia.com/Fixed-Networks/BBA/yang/"
          + "nokia-sdan-radius-dynamic-authorization-server";
  prefix "nokia-dyn-auth-server";

  import ietf-netconf-acm {
    prefix "nacm";
  }
  import ietf-inet-types {
    prefix "inet";
  }

  import nokia-yang-types {
    prefix "nok-typ";
  }

  organization
    "Nokia";

  contact
    "Comments or questions about this Nokia YANG module should be
     directed to <mailto:isam.yang@nokia.com>.";

  description
    "This module contains new nodes according to Nokia specific
     requirements for RADIUS Dynamic Authorization Server(DAS).
     Change of Authorization(CoA - Dynamically attach QoS profile
     to a VSI and VSI to the forwarder) and DM(Disconnect messages)
     handling from the Dynamic Authorization Client(DAC).

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not  to offer any or all of these
     products and to withdraw any or all of them at any future time.

     Copyright (C) 2024, Nokia. All Rights Reserved.";

  revision 2024-06-12 {
    description
      "Yang definition for Dynamic Authorization Server(DAS)";
    reference
      "RFC 4673";
  }

  container radius-dynamic-authorization-server {
    presence
      "The presence of this container indicates the configuration
      support of RADIUS Dynamic Authorization Server(DAS).";

    description
      "The configuration support for RADIUS Dynamic Authorization
      Server(DAS).";

    leaf-list listen-ports {
      type uint32;
      description
        "If configured the Dynamic Authorization Server(DAS)
        shall start listening on the configured UDP ports.
        For example 3799,1813 and 1700 to handle the dynamic
        authorization requests from the Dynamic Authorization
        Client(DAC).";
    }

    /* RADIUS Dynamic Authorization Client(DAC) configuration */
    container dynamic-auth-clients {
      presence
        "The presence of this container indicates the configuration
        support of Dynamic Authorization Clients(DACs).";
      description
        "The RADIUS Dynamic Authorization Clients(DACs) with which the
        Dynamic Authorization Server(DAS) shares a secret";

      list client {
        key name;
        leaf name {
          type nok-typ:nokia-string-ascii64;
          description
            "An arbitrary name uniquely identifying each RADIUS
            Dynamic Authorization Client(DAC) with which this Dynamic
            Authorization Server(DAS) communicates.";
        }
        unique "transport/udp/udp/address";

        choice transport {
          mandatory true;
          description
            "The transport-protocol-specific parameters for this Client.";
          case udp {
            container udp {
              description
                "UDP-specific configuration parameters for the Dynamic
                Authorization Client(DAC).";
              reference
                "RFC 5176:Dynamic Authorization Extensions to Remote
                Authentication Dial In User Service (RADIUS)";
              leaf address {
                type inet:host;
                mandatory true;
                description
                  "The IP address or Hostname of the Dynamic
                  Authorization Client(DAC).";
              }
              leaf shared-secret {
                type string;
                mandatory true;
                nacm:default-deny-all;
                description
                  "The shared secret, which is known to both the
                  Dynamic Authorization client(DAC) and Dynamic
                  Authorization Server(DAS).";
              }
            }
          }
        }

        description
          "Dynamic Authorization Client(DAC) with which the Dynamic
          Authorization Server(DAS) shares a secret.";

        leaf admin-state {
          type enumeration {
            enum down {
              description
                "The administrative state of the Dynamic Authorization
                Client(DAC) is Down.";
            }
            enum up {
              description
                "The administrative state of the Dynamic Authorization
                Client(DAC) is Up.";
            }
          }
          default up;
          description
            "Administrative state of the Dynamic Authorization
            Client(DAC).";
        }

        container statistics {
          config false;
          description
            "Contains the operational statistics of the
            Dynamic Authorization Client(DAC) maintained
            by the Dynamic Authorization Server(DAS).";
          reference
            "RFC 4673";

          leaf disconnect-requests {
            type uint32;
            description
              "The number of RADIUS Disconnect-Requests recieved
              from this Dynamic Authorization Client(DAC).";
          }
          leaf dup-disconnect-requests {
            type uint32;
            description
              "The number of duplicate RADIUS Disconnect-Request
              packets received from this Dynamic Authorization
              Client(DAC).";
          }
          leaf disconnect-acks {
            type uint32;
            description
              "The number of RADIUS Disconnect-ACK packets
              sent to this Dynamic Authorization Client(DAC).";
          }
          leaf disconnect-naks {
            type uint32;
            description
              "The number of RADIUS Disconnect-NAK packets
              sent to this Dynamic Authorization Client(DAC).";
          }
          leaf disconnect-malformed-requests {
            type uint32;
            description
              "The number of malformed RADIUS Disconnect-Request
              packets received from this Dynamic Authorization
              Client(DAC).
              Bad authenticators and unknown types are not included
              as malformed Disconnect-Requests.Malformed packets
              include packets with an invalid length.";
          }
          leaf disconnect-bad-authenticators {
            type uint32;
            description
              "The number of RADIUS Disconnect-Request packets
              that contained an invalid Authenticator field received
              from this Dynamic Authorization Client(DAC).";
          }
          leaf disconnect-packets-dropped {
            type uint32;
            description
              "The number of incoming Disconnect-Requests from this
              Dynamic Authorization Client(DAC) that are silently
              discarded for some reason other than malformed, bad
              authenticators or unknown types.";
          }
          leaf coa-requests {
            type uint32;
            description
              "The number of RADIUS CoA-Requests recieved from this
              Dynamic Authorization Client(DAC).";
          }
          leaf dup-coa-requests {
            type uint32;
            description
              "The number of duplicate RADIUS CoA-Requests recieved
              from this Dynamic Authorization Client(DAC).";
          }
          leaf coa-acks {
            type uint32;
            description
              "The number of RADIUS CoA-ACK packets
              sent to this Dynamic Authorization Client(DAC).";
          }
          leaf coa-naks {
            type uint32;
            description
              "The number of RADIUS CoA-NAK packets
              sent to this Dynamic Authorization Client(DAC).";
          }
          leaf coa-malformed-requests {
            type uint32;
            description
              "The number of malformed RADIUS CoA-Requests received
              from this Dynamic Authorization client(DAC).Bad
              authenticators and unknown types are not included as
              malformed COA-Requests.Malformed packets include
              packets with an invalid length.";
          }
          leaf coa-bad-authenticators {
            type uint32;
            description
              "The number of RADIUS CoA-Request packets that contained
              an invalid Authenticator field received from this
              Dynamic Authorization Client(DAC).";
          }
          leaf coa-packets-dropped {
            type uint32;
            description
              "The number of incoming CoA-Requests from this Dynamic
              Authorization Client(DAC) that are silently discarded
              for some reason other than malformed, bad
              authenticators or unknown types.";
          }
          leaf dac-unknown-types {
            type uint32;
            description
              "The number of incoming packets of unknown types which
              were received on the Dynamic Authorization
              Server(DAS).";
          }
        }
        reference
          "RFC 4673";
      }
      leaf coa-invalid-client-addresses {
        type uint32;
        config false;
        description
          "The number of CoA-Request packets received from unknown
          Dynamic Authorization Client(DAC) addresses.";
      }
      leaf disconnect-invalid-client-addresses {
        type uint32;
        config false;
        description
          "The number of Disconnect-Request packets received from
          unknown Dynamic Authorization Client(DAC) addresses.";
      }
    }
  }
}
