module bbf-mgmd-mounted {
  yang-version 1.1;
  namespace "urn:bbf:yang:bbf-mgmd-mounted";
  prefix bbf-mgmd-mounted;


  import bbf-yang-types {
    prefix bbf-yang;
  }

  import bbf-mgmd-types {
    prefix bbf-mgmd-types;
  }
  
  import ietf-interfaces-mounted {
    prefix if-mounted;
  }

  import ietf-inet-types {
    prefix inet;
  }

  import bbf-if-type-mounted {
    prefix bbfift-mounted;
  }
  
  import bbf-fiber-onu-emulated-mount {
     prefix onu;
  }

  import nokia-template-common {
    prefix template-common;
  }
           
  include bbf-mgmd-configuration-interface-to-router-mounted;
  include bbf-mgmd-configuration-interface-to-host-mounted;
  include bbf-mgmd-configuration-multicast-snoop-mounted;

  organization
    "Broadband Forum <https://www.broadband-forum.org>
     Common YANG Project Stream";

  contact
    "Comments or questions about this Broadband Forum YANG module
     should be directed to <mailto:help@broadband-forum.org>.

     Editor:      Joey Boyd, ADTRAN
                  <mailto:joey.boyd@adtran.com>

     Editor:      Ludwig Pauwels, Nokia
                  <mailto:ludwig.pauwels@nokia.com>

     PS Leader:   Michael Shaffer, Nokia
                  <mailto:michael.shaffer@nokia.com>

     PS Leader:   William Lupton, Broadband Forum
                  <mailto:wlupton@broadband-forum.org>";

  description
    "This module contains a collection of YANG definitions for 
     supporting the Broadband Forum requirements on layer 2 multicast 
     management as applicable to access network equipment. As such, 
     this module is specific to access network equipment (e.g., 
     BBF-specified Access Nodes and FTTdp DPUs).
    
     Specifically,this module contains a collection of YANG 
     definitions for supporting the Multicast Group Membership 
     Discovery (MGMD) Protocols. In particular, it describes objects 
     used for managing the Internet Group Management Protocol (IGMP) 
     and the Multicast Listener Discovery (MLD) protocol in systems 
     that act as a multicast proxy, snooper, or a snooper with proxy
     reporting.

     Copyright (c) 2016, Broadband Forum
     All rights reserved.

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-383; see
     the TR itself for full legal notices.";

  revision 2018-03-28 {
    description
      "Initial revision.
       * Approval Date:    see revision date above.
       * Publication Date: yyyy-mm-dd.";
    reference
      "TR-383: Common YANG Modules
               <https://www.broadband-forum.org/technical/download/
                        TR-383.pdf>";
  }

  feature mgmd-proxy {
    description
      "MGMD proxy functionality is supported.";
  }

  feature mgmd-snoop-transparent {
    description
      "MGMD snooping functionality is supported.";
  }

  feature mgmd-snoop-with-proxy-reporting {
    description
      "MGMD snooping with proxy reporting functionality is 
       supported.";
  }

  feature multicast-cac {
    description
      "Multicast Connection Admission Control (CAC) functionality is 
       supported.";
  }

  feature multicast-package {
    description
      "Multicast packages, i.e. a package of multicast channels, are 
       supported.";
  }

  feature multicast-preview {
    description
      "Multicast preview offers the possibility to join multicast 
       channels for a restricted period / restricted amount of 
       times.";
  }

  feature mgmd-group-ip-range {
    description
      "Use group ip range feature to allow configuring a range of 
       group-addresses in once.";
  }

  feature static-multicast-group {
    description
      "Support of static multicast groups. The existence of a static 
       multicast group is controlled via configuration and not via 
       dynamic protocol behavior.";
  }
  
  identity mgmd-mode {
    description
      "Defines the MGMD mode. The MGMD mode specifies how IGMP / MLD 
       packets are processed to manage a multicast tree within the 
       context of a Layer 2 forwarder.";
  }

  identity proxy {
    base mgmd-mode;
    description
      "A proxy device performing IGMP/MLD-based forwarding has a 
       single upstream interface and one or more downstream 
       interfaces. The upstream interface (in the direction of the 
       multicast tree) performs the host portion of IGMP/MLD 
       protocol and the downstream direction (away from the direction
       of the root of the multicast tree) performs the router portion 
       of the IGMP/MLD protocol.";
    reference
      "RFC 4605";
  }

  identity snoop-transparent {
    base mgmd-mode;
    description
      "A transparent snooper that forwards MGMD reports only to those
       ports where multicast routers are attached.";
    reference
      "RFC 4541";
  }
  
  identity snoop-with-proxy-reporting {
    base mgmd-mode;
    description
      "A snooper with proxy-reporting capability will perform report 
       summarization and query suppression in order to reduce the load
       on the upstream multicast router.";
    reference
      "RFC 4541 Section 2.1.1, bullet 2";
  }

  identity unmatched-mgmd-report-processing {
    description
      "When an MGMD membership report is received, and it requests to 
       join a group address for which there is no configuration data 
       in the system, then there are various alternative ways on how 
       to process the request.";
    reference
      "TR-101 - R-238";
  }
  
  identity unmatched-mgmd-report-discard {
    base unmatched-mgmd-report-processing;
    description
      "When an MGMD membership report is received, and it requests to 
       join a group address for which there is no configuration data 
       in the system, then the system will discard the request.";
    reference
      "TR-101 - R-238";
  }
  
  identity unmatched-mgmd-report-forward {
    base unmatched-mgmd-report-processing;
    description
      "When an MGMD membership report is received, and it requests to 
       join a group address for which there is no configuration data 
       in the system, then the system will forward the MGMD message as
       regular data.";
    reference
      "TR-101 - R-238";
  }
  
  identity unmatched-mgmd-report-snoop-or-proxy {
    base unmatched-mgmd-report-processing;
    description
      "When an MGMD membership report is received, and it requests to 
       join a group address for which there is no configuration data 
       in the system, then the system will still perform the 
       transparent snooper, snooper with proxy-reporting, or proxy 
       function and manage a multicast tree for it.";
  }
  
  typedef rate-limit-action-enum {
    type enumeration {
      enum "drop" {
        description
          "The action is to drop MGMD membership reports that if 
           granted would result in requiring more bandwidth than 
           available on the interface.";
      }
      enum "best-effort" {
        description
          "The action is to process MGMD membership reports even when 
           granting them would result in requiring more bandwidth than
           available on the interface. This can result in packet 
           loss.";
      }
    }
    description
      "Defines the action to be taken for received MGMD membership 
       reports that, if granted, would result in requiring more 
       bandwidth than available on the interface.";
  }

  typedef usage-limit {
    type union {
      type enumeration {
        enum "no-limit" {
          description
            "No limit is applied.";
        }
      } 
      type uint32;
    }
    description
      "Defines possible resource usage limitations where the 
       limitation can be expressed in a number.";
  }

augment '/onu:onus/onu:onu/onu:root' {
  when "derived-from-or-self (../onu:usage, 'template-common:node-actual-usage') or
        derived-from-or-self (../onu:usage, 'template-common:node-template-usage')" {
     description
       "it should be a node-actual-usage or node-from-template-usage ONU for multicast configuration";
  }

  container multicast {
    description
      "Multicast configuration.";
    container mgmd {
      description
        "MGMD configuration, i.e. configuration related to the IGMP 
         and/or MLD protocols.";

      list multicast-snoop-transparent-profile {
        if-feature "mgmd-snoop-transparent";
        key "name";
        description
          "Profile containing configuration data to be used by 
           systems configured in snoop transparent mode.";

        leaf name {
          type bbf-yang:string-ascii64;
          description
            "The name of a multicast snoop transparent profile.";
        }

        leaf-list protocol-version {
          type bbf-mgmd-types:mgmd-protocol-and-version;
          min-elements 1;
          description
            "Protocol(s) and/or protocol version(s) supported on the 
             various interfaces of the VPN.";
        }

        container interfaces-to-hosts-data {
          description
            "This container contains leafs that are applied to an
             interface when a system operates in snoop transparent 
             mode.";

          uses multicast-snoop;
        }
      }

      list multicast-snoop-with-proxy-reporting-profile {
        if-feature "mgmd-snoop-with-proxy-reporting";
        key "name";
        description
          "Profile containing configuration data to be used by 
           systems configured in snoop with proxy reporting mode.";

        leaf name {
          type bbf-yang:string-ascii64;
          description
            "The name of a multicast snoop with proxy reporting 
             profile.";
        }

        leaf-list protocol-version {
          type bbf-mgmd-types:mgmd-protocol-and-version;
          min-elements 1;
          description
            "Protocol(s) and/or protocol version(s) supported on the 
             various interfaces of the VPN.";
        }

        container interfaces-to-hosts-data {
          description
            "This container contains leafs that are applied to each 
             interface facing the multicast tree when a system is 
             configured for snoop with proxy reporting.";

          uses multicast-snoop;
        }

        container interface-to-router-data {
          description
            "This container contains leafs that are applied to each 
             interface away from the multicast tree when the system is
             configured for snoop with proxy reporting.";

          uses interface-to-router;
        }
      }

      list multicast-proxy-profile {
        if-feature "mgmd-proxy";
        key "name";
        description
          "Profile containing configuration data to be used by 
           multicast proxy switches. A proxy provides service between 
           a set of interfaces for which it acts as a router and a set
           of interfaces for which it acts as a host.";

        leaf name {
          type bbf-yang:string-ascii64;
          description
            "The name of a multicast proxy profile.";
        }

        leaf-list protocol-version {
          type bbf-mgmd-types:mgmd-protocol-and-version;
          min-elements 1;
          description
            "Protocol(s) and/or protocol version(s) supported on the 
             various interfaces of the VPN.";
        }

        container interfaces-to-hosts-data {
          description
            "This container contains leafs that are applied to each 
             interface facing the multicast tree when the system is  
             configured for proxy mode.";

          uses interface-to-host;
        }

        container interface-to-router-data {
          description
            "This container contains leafs that are applied to each 
             interface facing away from the multicast tree when the  
             system is configured for proxy mode.";

          uses interface-to-router;
        }
      }

      list multicast-vpn {
        key "name";
        description
          "Multicast Virtual Private Network (VPN). A multicast VPN
           defines the context of the multicast service.  A service 
           operator may choose to configure a single multicast VPN or 
           multiple multicast VPN (e.g., open access environment).";

        leaf name {
          type bbf-yang:string-ascii64;
          description
            "This object is the name associated with a particular
             multicast VPN (service context).";
        }

        leaf mode {
          type identityref {
            base mgmd-mode;
          }
          mandatory true;
          description
            "Identifies the MGMD mode to be applied for this VPN. The 
             MGMD mode specifies how IGMP / MLD packets are processed 
             to manage a multicast tree within the context of a Layer 
             2 forwarder.";
        }

        leaf multicast-proxy-profile-name {
          when '../mode = "bbf-mgmd-mounted:proxy"';
          if-feature "mgmd-proxy";
          type leafref {
            path "../../../../bbf-mgmd-mounted:multicast/bbf-mgmd-mounted:mgmd/bbf-mgmd-mounted:"
               + "multicast-proxy-profile/bbf-mgmd-mounted:name";
          }
          description
            "A reference to a MGMD proxy profile.";
        }

        leaf multicast-snoop-transparent-profile-name {
          when '../mode = "bbf-mgmd-mounted:snoop-transparent"';
          if-feature "mgmd-snoop-transparent";
          type leafref {
            path "../../../../bbf-mgmd-mounted:multicast/bbf-mgmd-mounted:mgmd/bbf-mgmd-mounted:"
               + "multicast-snoop-transparent-profile/bbf-mgmd-mounted:"
               + "name";
          }
          description
            "A reference to a MGMD snoop transparent profile.";
        }

        leaf multicast-snoop-with-proxy-reporting-profile-name {
          when '../mode = "bbf-mgmd-mounted:snoop-with-proxy-reporting"';
          if-feature "mgmd-snoop-with-proxy-reporting";
          type leafref {
            path "../../../../bbf-mgmd-mounted:multicast/bbf-mgmd-mounted:mgmd/bbf-mgmd-mounted:"
               + "multicast-snoop-with-proxy-reporting-profile/bbf-mgmd-mounted:name";
          }
          description
            "A reference to a MGMD snoop with proxy reporting 
             profile.";
        }

        leaf ip-version {
          type inet:ip-version;
          default "ipv4";
          description
            "The IP version identifies the type of IP-addresses used 
             within this VPN.";
        }

        choice ip-to-host {             
          when 'mode = "bbf-mgmd-mounted:proxy" or mode = "bbf-mgmd-mounted:snoop-'
             + 'with-proxy-reporting"';
          description
            "Provides the mechanism to add IP addressing information
             to the VPN. This data, if configured, shall be used in
             MGMD query messages sent on host interfaces. If not 
             configured then the proxy or snooper with proxy reporting
             will generate MGMD query messages with the IP address
             0.0.0.0 or the equivalent for IPv6.";

          case ip-address {
            leaf ipv4-address {
              when '../ip-version = "ipv4"';
              type inet:ipv4-address;
              default "0.0.0.0";
              description
                "This object specifies the IPv4 address to be used as
                 source IP address in query messages when mode is 
                 proxy or snoop-with-proxy-reporting.";
            }

            leaf ipv6-address {
              when '../ip-version = "ipv6"';
              type inet:ipv6-address;
              default "::";
              description
                "This object specifies the IPv6 address to be used as
                 as source IP address in query messages when mode is 
                 proxy or snoop-with-proxy-reporting.";
            }
          }
        }

        leaf unmatched-membership-report-processing {
          type identityref {
            base unmatched-mgmd-report-processing;
          }
          default "unmatched-mgmd-report-discard";
          description
            "This attribute specifies the multicast VPN behaviour when
             the system receives a membership report message for a 
             multicast channel for which there is no explicit 
             configuration in the multicast-channel list.

             When no multicast package is associated to a particular 
             multicast interface to a host, then an unmatched report 
             is a report on such an interface for a group address that
             is not configured in the multicast channel list.

             When a multicast package is associated to a particular 
             multicast interface to a host, then this package 
             controls authorization for all multicast channels for 
             which there is explicit configuration in the 
             multicast-channel list. This means, an MGMD report for a 
             multicast channel that exists in the multicast-channel 
             list and is not part of the host's package is never
             granted. Also in this case this leaf controls the 
             processing of reports for group addresses for which there
             is no explicit configuration in the multicast-channel 
             list.";
          reference
            "TR-101 - R-238";
        }

        leaf network-interface-for-unmatched-reports {
          type leafref {
            path "../bbf-mgmd-mounted:multicast-network-interface/bbf-mgmd-mounted:"
               + "name";
          }
          description
            "This object identifies the multicast network interface 
             involved for multicast group addresses for which there is
             no specific configuration. It is the interface that is 
             used to send MGMD reports, and inherent it is also the 
             interface from which the system will receive the related 
             multicast packets.";
        }

        list multicast-interface-to-host {
          key "name";
          unique "vlan-sub-interface";
          description
            "This list contains configuration data for multicast 
             interfaces to hosts. A multicast interface to a host is 
             connecting a MGMD host to the multicast switch. A 
             multicast interface to a host is characterized by the 
             need to perform some checks before granting requests to 
             join a multicast address.";

          leaf name {
            type bbf-yang:string-ascii64;
            must '(count(../../bbf-mgmd-mounted:multicast-network-interface
[bbf-mgmd-mounted:name = current()]) = 0)' {
              error-message
                "The name of a multicast interface to host can not be
                 the name of a multicast network interface.";

              description
                "Only allow unique names over both the list of
                 multicast to network interfaces and the multicast 
                 interfaces to host.";
            }            
            description
              "The name of the multicast interface to a host.";
          }

          leaf vlan-sub-interface {
            type leafref { path '../../../../../if-mounted:interfaces/if-mounted:interface/if-mounted:name'; }
            must "derived-from-or-self(../../../../../if-mounted:interfaces/if-mounted:interface
                  [if-mounted:name = current()]/if-mounted:type,
                  'bbfift-mounted:vlan-sub-interface')" {
                description 
                  "The interface must be of the type 
                   'vlan-sub-interface'.";
              }  
            mandatory true;
            description
              "This object specifies the VLAN sub-interface on a 
               host interface.";
          }

          leaf data-path-vlan-sub-interface {
            type leafref { path '../../../../../if-mounted:interfaces/if-mounted:interface/if-mounted:name'; }
            must "derived-from-or-self(../../../../../if-mounted:interfaces/if-mounted:interface
                  [if-mounted:name = current()]/if-mounted:type,
                  'bbfift-mounted:vlan-sub-interface')" {
                description 
                  "The interface must be of the type VLAN 
                   sub-interface.";
              }		  

            description
              "This object specifies the VLAN sub-interface to be used
               when the multicast function needs knowledge on a 
               related datapath. E.g. for re-inserting MGMD reports 
               for multicast group adresses for which there is no 
               configuration. Further packet processing, including 
               VLAN tag popping and or pushing, is subject to 
               configuration of the referenced VLAN sub-interface.";
          }        

          leaf max-group-number {
            type usage-limit;
            default "no-limit";
            description
              "This attribute specifies the maximum number of dynamic
               multicast groups that may be replicated to the 
               interface at any one time. Dynamic refers to including 
               all multicast groups requested via MGMD reports, and
               excludes all the static multicast branches. The 
               default value  no-limit' means that no administrative 
               limit is imposed.";
          }

          leaf multicast-rate-limit {
            if-feature "multicast-cac";
            type uint32;
            units "kbits/second";
            default "0";
            description
              "The multicast rate limit specifies the total bandwidth 
               available on the interface for multicast traffic.";
          }

          leaf multicast-rate-limit-exceed-action {
            if-feature "multicast-cac";
            type rate-limit-action-enum;
            default "best-effort";
            description
              "The multicast rate limit exceed action specifies how a 
               multicast switch shall act when the multicast CAC 
               concludes that accepting the MGMD request would result
               in a situation that more bandwith is needed than 
               available on the host interface, then this 
               request can be accepted, possibly resulting in packet 
               loss, or the request can be dropped.";
          }

          leaf-list multicast-package {
            if-feature multicast-package;
            type leafref {
              path "../../bbf-mgmd-mounted:multicast-package/bbf-mgmd-mounted:name";
            }
            description
              "References the packages of multicast channels to which 
               the host has a subscription. If packages are 
               associated to a multicast interface to a host, then 
               these defines the multicast channels that are 
               authorized. If no package is associated to a multicast 
               interface to a host, then the full list of multicast 
               channels of the VPN is authorized.";
          }

          action clear-host-interface-stats {
            description
              "When the action is received, the statistics within the 
               multicast interface to a host are cleared.";
          }
        }

        list multicast-network-interface {
          key "name";
          description
            "This list contains the network topology dependent 
             configuration data a multicast switch needs to reach MGMD
             routers. This basicaly provides the list of network 
             interfaces via which it can reach them and in case the 
             multicast switch acts as a proxy or as a snooper with 
             proxy reporting it also provides the IP address.";

          leaf name {
            type bbf-yang:string-ascii64;
            description
              "The name of the multicast network interface.";
          }

          choice multicast-transport {
            mandatory true;
            description
              "Provides the various choices for how multicast traffic 
               can be distributed up to the multicast switch.";
            case single-uplink {
              container single-uplink-interface-data {
                description
                  "Contains the data for when the multicast has a 
                   single VLAN sub-interface as network interface.";
                leaf vlan-sub-interface {
                  type leafref { path '../../../../../../if-mounted:interfaces/if-mounted:interface/if-mounted:name'; }
                  must
                    "derived-from-or-self(../../../../../../if-mounted:interfaces
                     /if-mounted:interface[if-mounted:name = current()]/if-mounted:type,
                     'bbfift-mounted:vlan-sub-interface')" {
                    description 
                      "The single uplink via which the multicast 
                       traffic enters the switch shall be a VLAN 
                       sub-interface on a network interface.";
                  }  

                  description
                    "This object specifies the VLAN sub-interface via 
                     which the multicast channel is distributed to the
                     multicast switch.";
                }
              }
            }
          } 

          choice ip-layer {             
            when '../mode = "bbf-mgmd-mounted:proxy" or
                  '
               + '../mode = "bbf-mgmd-mounted:snoop-with-proxy-reporting"';
            description
              "Provides the mechanism to add IP addressing information
               to the multicast network interface.";

            case ip-address {
              leaf ipv4-address {
                when '../../ip-version = "ipv4"';
                type inet:ipv4-address;
                default "0.0.0.0";
                description
                  "This object specifies the IPv4 address to be used 
                   as source IP addess when mode is proxy or 
                   snoop-with-proxy-reporting.";
              }

              leaf ipv6-address {
                when '../../ip-version = "ipv6"';
                type inet:ipv6-address;
                default "::";
                description
                  "This object specifies the IPv6 address to be used 
                   as source IP addess when mode is proxy or 
                   snoop-with-proxy-reporting.";
              }
            }
          }
          
          action clear-network-interface-stats {
            description
              "When the action is received, the statistics within the 
               multicast network interface are cleared.";
          }
        }

        list multicast-channel {
          key "name";
          unique "ipv4/group-ipv4-address ipv4/source-ipv4-address";
          unique "ipv6/group-ipv6-address ipv6/source-ipv6-address";

          description
            "This list contains management information of multicast 
             channels for Any Source Multicast (ASM) and Source 
             Specific Multicast (SSM) mode of operations. Multicast 
             channels are uniquely identified by the source and
             multicast group IP address.";

          leaf name {
            type bbf-yang:string-ascii64;
            description
              "This object is the name associated with a particular
               multicast channel.";
          }

          leaf network-interface {
            type leafref {
              path "../../bbf-mgmd-mounted:multicast-network-interface/bbf-mgmd-mounted:name";
            }
            mandatory true;
            
            description
              "This object specifies the multicast network interface 
               on which the multicast channel is received.";
          }

          container ipv4 {
            description
              "Container for all IPv4 dependent configuration data.";
              
            leaf source-ipv4-address {
              when '../../../ip-version = "ipv4"';
              type inet:ipv4-address;
              default "0.0.0.0";
              description
                "The source IP address of the multicast channel. A
                 value '0.0.0.0' is used in the ASM mode of operation.
                 A value different of '0.0.0.0' is used in the SSM 
                 mode of operation.";
            }

            leaf group-ipv4-address {
              when '../../../ip-version = "ipv4"';
              type inet:ipv4-address;
              mandatory true;
              description
                "The group IP address of the multicast channel.";
            }

            leaf group-ipv4-address-end {
              when '../../../ip-version = "ipv4"';
              if-feature mgmd-group-ip-range;
              type inet:ipv4-address;
              description
                "If the leaf group-ipv4-address-end is not present, 
                 then the configuration is for a single group address 
                 as specified in the leaf 'group-ipv4-address'.

                 A group-ipv4-address-end with a value lower than the 
                 leaf group-ipv4-address is invalid.

                 A group-ipv4-address-end with a value greater that 
                 the group-ipv4-address is valid and then the 
                 configurationis for all the group addresses starting 
                 from group-ipv4-address up to and including the 
                 group-ipv4-address-end.";
            }
          }

          container ipv6 {
            description
              "Container for all IPv6 dependent configuration data.";
              
            leaf source-ipv6-address {
              when '../../../ip-version = "ipv6"';
              type inet:ipv6-address;
              default "::";
              description
                "The source IP address of the multicast channel. A
                 value '::' is used in the ASM mode of operation. A 
                 value different of '::' is used in the SSM mode of 
                 operation.";
            }

            leaf group-ipv6-address {
              when '../../../ip-version = "ipv6"';
              type inet:ipv6-address;
              mandatory true;
              description
                "The group IP address of the multicast channel.";
            }

            leaf group-ipv6-address-end {
              when '../../../ip-version = "ipv6"';
              if-feature mgmd-group-ip-range;
              type inet:ipv6-address;
              description
                "If the leaf group-ipv6-address-end is not present,
                 then the configuration is for a single group address 
                 as specified in the leaf 'group-ipv6-address'.

                 A group-ipv6-address-end with a value lower than the 
                 leaf group-ipv6-address is invalid.

                 A group-ipv6-address-end with a value greater that 
                 the group-ipv6-address is valid and then the 
                 configuration is for all the group addresses starting
                 from group-ipv6-address up to and including the 
                 group-ipv6-address-end.";
            }
          }

          leaf channel-rate {
            if-feature "multicast-cac";
            type uint32;
            units "kbits/second";
            default "0";
            description
              "The bandwidth of the multicast channel to be used at 
               CAC.";
          }

          leaf-list interface-to-host {
            if-feature static-multicast-group;
            type leafref {
              path "../../bbf-mgmd-mounted:multicast-interface-to-host/bbf-mgmd-mounted:name";
            }

            description
              "This object specifies the interface in which the
               multicast channel is received.";
          }          
        }

        list multicast-package {
          if-feature multicast-package;
          key "name";
          description
            "Each entry contains the information related to a 
             multicast package, i.e. a package of multicast 
             channels.";

          leaf name {
            type bbf-yang:string-ascii64;
            description
              "The name of a multicast package.";
          }

          leaf-list multicast-channel-list {
            type leafref {
              path '../../bbf-mgmd-mounted:multicast-channel/bbf-mgmd-mounted:name';
            }
            description
              "This list indicates which multicast channels belong to 
               this package.";
          }

          leaf is-preview {
            if-feature multicast-preview;
            type boolean;

            default false;

            description
              "The value 'true' indicates the multicast channels of 
               this package can be joined as controlled by the preview
               configuration data. The value 'false' indicates the 
               multicast channels can be joined unlimited.";
          }

          leaf preview-repeat-time {
            when '../is-preview = "true"';
            if-feature multicast-preview;
            type uint32;
            units "seconds";
            default "0";

            description
              "The minimum time in seconds between two previews of a
               given multicast channel.";
          }

          leaf preview-repeat-count {
            when '../is-preview = "true"';
            if-feature multicast-preview;
            type usage-limit;
            default "3";
            description
              "The maximum number of times a given multicast channel
               may be previewed.";
          }

          leaf preview-reset-time {
            when '../is-preview = "true"';
            if-feature multicast-preview;
            type uint32;
            units "minutes";
            default "0";
            description
              "Identifies the moments at which the preview repeat 
               counter is reset. The moments are identified as 
               follows: reset happens each day at the moment specified
               by taking the number of minutes as specified by this 
               leaf after midnight. E.g. a value of 0 results in a 
               reset at midnight local time, a value of 60 results in 
               a reset at 1h00.";
          }

          leaf preview-length {
            when '../is-preview = "true"';
            if-feature multicast-preview;
            type uint32;
            units "seconds";
            default "180";

            description
              "The maximum duration of each preview in seconds.";
          }
        }

        action clear-vpn-stats {
          description
            "When the action is received, the statistics within the
             multicast VPN are cleared.";
        }
      }
    }  
  }
 }
}
