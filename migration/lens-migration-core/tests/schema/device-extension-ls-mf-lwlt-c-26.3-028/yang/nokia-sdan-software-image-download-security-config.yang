module nokia-sdan-software-image-download-security-config {
  yang-version 1.1;
  namespace "http://www.nokia.com/Fixed-Networks/BBA/yang/"
          + "nokia-sdan-software-image-download-security-config";
  prefix nokia-software;

  import ietf-trust-anchors {
    prefix ta;
  }

  import nokia-sdan-keystore-types {
    prefix nokia-ks;
  }

  import nokia-sdan-est-client {
    prefix estc;
  }

  organization
    "Nokia";

  contact
    "isam.yang@nokia.com";

  description
    "The NOKIA IETF/System YANG module supporting
     deviations on top of standard.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.

     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not to offer any or all of these
     products and to withdraw any or all of them at any future time.

     Copyright (C) 2025, Nokia. All Rights Reserved.";

   revision 2025-11-28 {
     description
       "Initial Revision";
     reference
      "Nokia specific";
   }

   container software-certificates {
    description
      "Configuration container for software certificates.";

        choice server-key-choice {
           description "Choice between a server-public-key and an EST certificate profile";
	     case server-public-key {
	       leaf server-public-key {
                 if-feature ta:x509-certificates;
                   type ta:pinned-certificates-ref;
                     description
                       "A reference to a list of certificate authority (CA)
                       certificates used while download using https.";
               }
             }
	     case est-certificate-profile-key-reference {
	       container est-ca-certificate-profile-reference {
                  uses estc:est-certificate-profile-ref-grouping;
                  description
                    "Reference to an EST CA certificate profile configuration.";
               }
           }
        }

        choice certificate-reference-choice {
           description "Choice between a central keystore reference and an EST certificate profile";
             case central-keystore-reference {
               container central-keystore-reference {
                 uses nokia-ks:asymmetric-key-certificate-ref-grouping;
                   description
                     "A reference to a specific certificate associated with an asymmetric key, referenced cert-key pair is used for mTLS
                     file transfer and encryption of the configuration file.";
                }
	      }
	      case est-certificate-profile-reference {
	    	container est-certificate-profile-reference {
                  uses estc:est-certificate-profile-ref-grouping;
                    description
                      "Reference to an EST certificate profile configuration for mTLS file transfer, referenced EST certificate is used for the encryption of the configuration file.";
                }
	      }
	   }
  }

}
