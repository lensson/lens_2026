module nokia-sdan-dhcpv4-client-simulator {
  yang-version 1.1;
  namespace "http://www.nokia.com/Fixed-Networks/BBA/yang/"
          + "nokia-sdan-dhcpv4-client-simulator";

  prefix dhcpv4-client-sim;

  import nokia-sdan-dhcp-client-simulator-types {
    prefix dhcp-client-sim-types;
  }

  import nokia-sdan-client-simulator-types {
    prefix client-simulator-types;
  }

  import ietf-interfaces {
    prefix "if";
  }

  import ietf-netconf-acm {
    prefix nacm;
  }

  import bbf-if-type {
    prefix "bbfift";
  }

  import ietf-yang-types {
     prefix yang;
  }

  import bbf-interface-usage {
    prefix bbf-if-usg;
  }

  import bbf-vlan-sub-interface-vector {
      prefix bbf-vsi-vctr;
  }

  import bbf-vlan-sub-interface-vector-usage {
      prefix bbf-vsi-vctr-usg;
  }

  organization
    "Nokia";

  contact
    "Comments or questions about this Nokia YANG module should be
     directed to <mailto:isam.yang@nokia.com>.";

  description
    "This module contains new nodes according to Nokia specific
     requirements for DHCP Client session simulation.

     This specification is published by Nokia under Non-Disclosure
     Agreement(s) (NDA) with specific parties and has to be considered
     as Confidential Information as defined in such NDA. Nokia
     reserves the right to revise this document for any reason,
     including but not limited to conformity with standards
     promulgated by various agencies, utilisation of advances in the
     state of the technical areas, or the reflection of changes in the
     design of any equipment, techniques, or procedures described or
     referred to herein.

     The product specifications and other technical or performance
     information contained herein are subject to change without
     notice. Updates of this document will be issued under the above
     NDA's.


     Nokia makes no representation or warranty, expressed or implied,
     with respect to the sufficiency, accuracy, or utility of any
     information or opinion contained herein. Nokia expressly advises
     that any use of for any purpose or reliance upon this technical
     reference is at the risk of the user and that Nokia shall not be
     liable for any damage or injury incurred by any person arising
     out of the sufficiency, accuracy, or utility of any information
     or opinion contained herein.

     This document is not to be construed as a suggestion to any
     manufacturer to modify or change any of its products, nor does
     this document represent any commitment by Nokia to sell or
     purchase any product. Nothing contained herein shall be construed
     as conferring by implication, estoppel, or otherwise any license
     or right under any patent, whether or not the use of any
     information herein necessarily employs an invention of any
     existing or later issued patent.

     Nokia reserves the right not  to offer any or all of these
     products and to withdraw any or all of them at any future time.

     Copyright (C) 2022, Nokia. All Rights Reserved.";

  revision 2023-07-17 {
    description
      "Added error-message for client-mac.";
    reference
      "";
  }

  revision 2023-04-05 {
    description
      "client-mac should not allow any multicast address or broadcast address";
    reference
      "";
  }

  revision 2022-09-21 {
    description
      "Initial version";
    reference
      "";
  }

  container dhcpv4-client-simulator {
    presence
      "Presence of this container indicates that DHCP sessions are
       simulated on the User vlan-sub-interfaces.";
    description
      "Simulate DHCP Client sessions operations and operational
       parameters.";

    list session {
      key interface;

      description
        "Defines the simulated DHCP client session per
         vlan-sub-interface.";

      leaf interface {
        type string;
/*
        type if:interface-ref;
        must "derived-from-or-self("
           + "/if:interfaces/if:interface[if:name = current()]"
           + "/if:type,'bbfift:vlan-sub-interface') and "
           + "(/if:interfaces/if:interface[if:name = current()]"
           + "/bbf-if-usg:interface-usage/bbf-if-usg:"
           + "interface-usage = 'user-port'"
           + " or "
           + "/bbf-vsi-vctr:vsi-vector-profiles/bbf-vsi-vctr:vsi-vector-profile[bbf-vsi-vctr:name = "
           + "/if:interfaces/if:interface[if:name = current()]/bbf-vsi-vctr:vector-profile]/"
           + "bbf-vsi-vctr-usg:interface-usage/bbf-vsi-vctr-usg:interface-usage = 'user-port')" {

          error-message
            "Only interfaces of type 'vlan-sub-interface' and
             interface-usage 'user-port' can be used to simulate DHCP
             client session";
          description
            "Allows DHCP client session simulation initiation only on
             user vlan-sub-interface.";
          }
*/
        description
          "The user vlan-sub-interface on which the dhcp client
           simulation is to be performed. Removing the interface while
           an active simulated session is available, would remove the
           dhcp client session implicitly";
      }

      action start-client-session {
        nacm:default-deny-all;
        description
          "Specify the DHCPv4 Client session simulation start action.
           Upon execution of the action, DHCP IP acquire process is
           initiated by sending the DHCP Discovery message to the DHCP
           Server as if it had originated from an actual user on the
           configured vlan-sub-interface. As a result further DHCP
           messages offer, request and acknowledgement are exchanged
           with the DHCP Server to acquire the IP address.

           If a DHCP client session is already in-progress or active,
           new action command will be rejected. Stop action is
           suggested when a session is already in-progress/active.

           If previously executed session-status is failure, new action
           command will be accepted.";

        input {

          leaf client-mac {
            type yang:mac-address {
		pattern "[0-9a-fA-F][02468aAcCeE](:[0-9a-fA-F]{2}){5}" {
                  error-message
                    "Invalid MAC Address format or Multicast/Broadcast address as client-mac"
                    + " are not supported";
           }
	}
            mandatory true;
            description
              "MAC address of the Client(chaddr).It is the hardware
              address of the Client used for transmission of DHCP
              Reply messages from the DHCP Server.";
            reference
              "RFC 2131 section 2 (chaddr, client's hardware address)";
          }

          leaf option-60 {
            type string{
              length "1..64";
            }
            description
              "The Vendor class identifier (option 60) is used by DHCP
               clients to optionally identify the vendor type and
               configuration of a DHCP client.";
            reference
              "RFC 2132 section 9.13 (Vendor class identifier).";
          }
          container option-61 {
            description
              "The Client-identifier (option 61) is used by DHCP
               clients to specify their unique identifier. The DHCP
               Server uses this unique identifer to associate the
               Client with its IP lease.

               If the client does not provide the Client-identifier
               option, the DHCP server will use the client mac-address
               to identify the client.";
            reference
              "RFC 2132 section 9.14 (Client-identifier).";

            choice client-identifier {
              description
                "Selects the Client-identifer for the DHCP Client.";
              case mac-address {
                leaf mac-address {
                  type yang:mac-address;
                  description
                    "Configures the mac-address as the unique client
                     identifier.";
                }
              }
              case string {
                leaf string {
                  type string{
                    length "1..64";
                  }
                  description
                    "Configures a string as the unique client
                     identifier.";
                }
              }
            }
          }
          uses client-simulator-types:simulation-vlan-tag-params;
          leaf time-out {
            type client-simulator-types:time-out;
            description "time out";
          }
        }
      }
      action stop-client-session {
        nacm:default-deny-all;
        description
          "Specify the DHCP test stop action. The stop action
           terminates and disables the DHCP Client session simulation
           which is running on the User vlan-sub-interface. It also
           removes the state data and clears the client device and the
           input parameters provided as part of the start action.";
      }
      container session-status {
        config false;
        description
          "Defines the state data for the simulated DHCP Client
           session.";

        uses dhcp-client-sim-types:session-status-params;
      }
    }
  }
}
